;;; Local AutoCAD/ChatGPT bridge. No network, COM, native modules or GUI automation.
;;; Load this file, then run CHATGPT. Esc releases the command line.
(setq cg:root "__BRIDGE_ROOT__/")

(defun cg:path (name) (strcat cg:root name))
(defun cg:write (name lines / f)
  (setq f (open (cg:path (strcat name ".tmp")) "w"))
  (if (not f) (exit))
  (foreach line lines (write-line line f))
  (close f)
  (vl-file-delete (cg:path name))
  (vl-file-rename (cg:path (strcat name ".tmp")) (cg:path name)))
(defun cg:doc () (strcat (getvar "DWGPREFIX") (getvar "DWGNAME")))
(defun cg:heartbeat ()
  (cg:write "session.txt" (list cg:session (cg:doc) (getvar "ACADVER"))))
(defun cg:reply (id state value)
  (cg:write "result.txt" (list id state (vl-prin1-to-string value))))
(defun cg:eval (code) (eval (read code)))
(defun cg:request (/ f raw req id value mutation begun)
  (if (findfile (cg:path "request.txt"))
    (progn
      (setq f (open (cg:path "request.txt") "r"))
      (setq raw (read-line f)) (close f)
      ;; Claim before evaluation. Claimed requests are NEVER retried automatically.
      (vl-file-delete (cg:path "running.txt"))
      (if (vl-file-rename (cg:path "request.txt") (cg:path "running.txt"))
        (progn
          (setq req (vl-catch-all-apply 'read (list raw)))
          (if (or (vl-catch-all-error-p req) (/= (type req) 'LIST) (/= (length req) 5))
            (cg:reply "invalid" "error" "Malformed request")
            (progn
              (setq id (nth 0 req))
              (cond
                ((/= (nth 1 req) cg:session) (cg:reply id "error" "Session changed; request rejected"))
                ((/= (nth 2 req) (cg:doc)) (cg:reply id "error" "Active drawing changed; request rejected"))
                (T
                  (setq mutation (= (nth 3 req) "write"))
                  (if mutation (progn (command-s "_.UNDO" "_Begin") (setq begun T)))
                  (setq value (vl-catch-all-apply 'cg:eval (list (nth 4 req))))
                  (if begun (command-s "_.UNDO" "_End"))
                  (if (vl-catch-all-error-p value)
                    (cg:reply id "error" (vl-catch-all-error-message value))
                    (cg:reply id "ok" value))))))
          (vl-file-delete (cg:path "running.txt")))))))

(defun c:CHATGPT (/ *error* oldecho tick)
  (setq oldecho (getvar "CMDECHO"))
  (defun *error* (message)
    (setvar "CMDECHO" oldecho)
    (vl-file-delete (cg:path "session.txt"))
    (princ "\nChatGPT disconnected. Manual control restored.") (princ))
  (if (findfile (cg:path "session.txt"))
    (princ "\nA bridge session already exists. Stop it before starting another.")
    (progn
      (setq cg:session (strcat (rtos (getvar "DATE") 2 8) "-" (itoa (getvar "MILLISECS"))))
      (vl-file-delete (cg:path "request.txt"))
      (vl-file-delete (cg:path "running.txt"))
      (vl-file-delete (cg:path "stop.txt"))
      (setvar "CMDECHO" 0)
      (princ "\nChatGPT direct bridge active. Press Esc for manual control.")
      (setq tick 0)
      (cg:heartbeat)
      (while (not (findfile (cg:path "stop.txt")))
        (cg:request)
        (command-s "_.DELAY" 100)
        (setq tick (1+ tick))
        (if (= (rem tick 10) 0) (cg:heartbeat)))
      (vl-file-delete (cg:path "session.txt"))
      (vl-file-delete (cg:path "stop.txt"))
      (setvar "CMDECHO" oldecho)
      (princ "\nChatGPT disconnected. Manual control restored.")))
  (princ))
(princ "\nChatGPT bridge loaded. Type CHATGPT to connect; Esc to disconnect.")
(princ)
