;;; S16 R15 médiafal – 3D szerkezeti modell (generálva: 2026-10-30, f2_cad_export.py)
;;; STÁTUSZ: TERVI MODELL – nem gyártási kiadás. Forrás: parts_v1.json (S16-R15C-GY-v1).
;;; ActiveX (vla-*) nélkül: csak parancs + entmake – AutoCAD for Mac-en is fut.
;;; Használat: APPLOAD → ezt a fájlt → parancssor: (s16-build)   majd ellenőrzés: (s16-readback "<mappa>")
;;; Egység: mm. KOORDINÁTA: Y_CAD = -Y_helyi (egyetlen tükrözés). Az R14 helyi rendszer (X jobbra a szobából, Y faltól a szoba
;;; felé, Z fel) balkezes; jobbkezes AutoCAD-ben e nélkül a bútor tükörképe épülne. Így a fal síkja Y=0, a front -Y felé néz,
;;; az AutoCAD FRONT nézet = szobából nézett homlokzat (torony bal oldalt).

(defun s16-env ()
  (setvar "CMDECHO" 0) (setvar "OSMODE" 0) (setvar "INSUNITS" 4) (setvar "DELOBJ" 1)
  (command "_.UCS" "_W"))

(defun s16-layer (name col)
  (if (not (tblsearch "LAYER" name))
    (if (= (type col) 'STR) (command "_.-LAYER" "_M" name "_C" "_T" col "" "") (command "_.-LAYER" "_M" name "_C" (itoa col) "" ""))
    (command "_.-LAYER" "_S" name ""))
  (setvar "CLAYER" name))

(defun s16-box (x y z dx dy dz)
  (command "_.BOX" (list x y z) (list (+ x dx) (+ y dy) (+ z dz)))
  (entlast))

;; zárt LWPOLYLINE a WCS XY síkban; pts = ((u v bulge) ...)
(defun s16-lwpoly (pts / d)
  (setq d (list '(0 . "LWPOLYLINE") '(100 . "AcDbEntity") '(100 . "AcDbPolyline") (cons 90 (length pts)) '(70 . 1)))
  (foreach p pts (setq d (append d (list (list 10 (car p) (cadr p)) (cons 42 (caddr p))))))
  (entmake d)
  (entlast))

;; profil (U=X, V=Z) kihúzása T-vel, X körüli +90°-os forgatás: (u v n) -> (u -n v), majd tolás (x0 y0 z0)
(defun s16-extrude-y (pts tt x0 y0 z0 / pl s)
  ;; y0 itt már CAD-koordináta (= -Y_helyi), a test y0-tt .. y0 között lesz
  (setq pl (s16-lwpoly pts))
  (command "_.EXTRUDE" pl "" tt)
  (setq s (entlast))
  (command "_.ROTATE3D" s "" "_X" '(0 0 0) 90)
  (command "_.MOVE" s "" '(0 0 0) (list x0 y0 z0))
  s)

(defun s16-sub (a b) (command "_.SUBTRACT" a "" b "") a)

;; henger két pont között (tengely), r sugár – furatokhoz, tiplikhez
(defun s16-cyl (x y z r x2 y2 z2) (command "_.CYLINDER" (list x y z) r "_A" (list x2 y2 z2)) (entlast))

;; blokk a megadott (a 0 rétegen, WCS-origóban épített) testekből; ha már létezik, a testeket törli
(defun s16-blk (name ents / ss)
  (setq ss (ssadd))
  (foreach e ents (if e (ssadd e ss)))
  (if (tblsearch "BLOCK" name) (command "_.ERASE" ss "") (command "_.-BLOCK" name '(0 0 0) ss ""))
  name)

;; blokkhivatkozás tetszőleges térbeli irányba: a blokk +Z tengelye = dir (WCS), a pont WCS-ben
(defun s16-ins (name lay pt dir rot xs)
  (entmake (list (cons 0 "INSERT") (cons 2 name) (cons 8 lay) (cons 10 (trans pt 0 dir))
                 (cons 41 xs) (cons 42 1.0) (cons 43 1.0) (cons 50 rot) (cons 210 dir))))

(defun s16-count-ins (name / ss) (setq ss (ssget "_X" (list (cons 0 "INSERT") (cons 2 name)))) (if ss (sslength ss) 0))

(defun s16-count (pre / ss i n e)
  (setq ss (ssget "_X" '((0 . "3DSOLID"))) i 0 n 0)
  (if ss (while (< i (sslength ss)) (setq e (ssname ss i)) (if (wcmatch (cdr (assoc 8 (entget e))) (strcat pre "*")) (setq n (1+ n))) (setq i (1+ i))))
  n)

(defun s16-copy (e / last) (setq last (entlast)) (command "_.COPY" e "" '(0 0 0) '(0 0 0)) (entlast))

(defun s16-safe (s / r i c)
  ;; fájlnévhez: $ és # → _ (vl-string-* nélkül, Mac-kompatibilis)
  (setq r "" i 1)
  (while (<= i (strlen s))
    (setq c (substr s i 1))
    (setq r (strcat r (if (member c '("$" "#")) "_" c)) i (1+ i)))
  r)

(defun s16-readback (dir / ss i e lay n)
  ;; minden $PART_ 3D test MASSPROP-ja külön fájlba: <dir>/<réteg>.mpr (AutoCAD tömegjellemző-szöveg, NEM woodWOP MPR)
  (setvar "FILEDIA" 0)
  (setq ss (ssget "_X" '((0 . "3DSOLID"))) i 0 n 0)
  (if ss
    (while (< i (sslength ss))
      (setq e (ssname ss i) lay (cdr (assoc 8 (entget e))))
      (if (= (substr lay 1 6) "$PART_")
        (progn (command "_.MASSPROP" e "" "_Y" (strcat dir "/" (s16-safe lay))) (setq n (1+ n))))
      (setq i (1+ i))))
  (setvar "FILEDIA" 1)
  (princ (strcat "\nS16 readback: " (itoa n) " test kiirva ide: " dir))
  (princ))

(defun s16-smoketest ( / a b c)
  ;; parancs-próba a teljes build előtt: hasáb, íves (bulge) kihúzás, kivonás – várt értékek a 30_eredmenyek-ben
  (s16-env)
  (s16-layer "$PART_SMOKE_BOX#0000" 3)
  (setq a (s16-box 0 -300 0 400 18 600))
  (s16-layer "$PART_SMOKE_ARC#0000" 4)
  (setq c (s16-extrude-y (list (list 0 0 0) (list 100 0 0.414213562) (list 200 100 0) (list 200 200 0) (list 0 200 0)) 18 600 -18 0))
  (s16-layer "$PART_SMOKE_SUB#0000" 5)
  (setq a (s16-box 1000 -300 0 400 18 600))
  (setq b (s16-box 1100 -310 100 200 38 400))
  (s16-sub a b)
  (command "_.ZOOM" "_E")
  (princ "\nS16 smoketest kesz: 3 test. Futtasd: (s16-readback \"<mappa>\")")
  (princ))

(defun s16-build ( / a b)
  (s16-env)
  ;; D1-L
  (s16-layer "$PART_S16_D1-L\U+02D90\U+02D90\U+00A8V000\U+02D90\U+00A8#0\U+00A816001" "80,73,66")
  (setq a (s16-box 435 -377 168 18 337 402))
  (s16-layer "SZINES_Oldal" 40)
  (command "_.COPY" a "" '(0 0 0) '(5100 0 0)) (command "_.CHPROP" (entlast) "" "_LA" "SZINES_Oldal" "")
  ;; D1-R
  (s16-layer "$PART_S16_D1-R\U+02D90\U+02D90\U+00A8V000\U+02D90\U+00A8#0\U+00A816002" "80,73,66")
  (setq a (s16-box 852 -377 168 18 337 402))
  (s16-layer "SZINES_Oldal" 40)
  (command "_.COPY" a "" '(0 0 0) '(5100 0 0)) (command "_.CHPROP" (entlast) "" "_LA" "SZINES_Oldal" "")
  ;; D1-T
  (s16-layer "$PART_S16_D1-T\U+02D90\U+02D90\U+00A8FF00\U+02D90\U+00A8#0\U+00A816003" "51,44,38")
  (setq a (s16-box 453 -377 552 399 337 18))
  (s16-layer "SZINES_Tet\U+0151" 173)
  (command "_.COPY" a "" '(0 0 0) '(5100 0 0)) (command "_.CHPROP" (entlast) "" "_LA" "SZINES_Tet\U+0151" "")
  ;; D1-BACK
  (s16-layer "$PART_S16_D1-BACK\U+02D90\U+02D90\U+00A80000\U+02D90\U+00A8#0\U+00A816004" "105,108,103")
  (setq a (s16-box 453 -48 168 399 8 384))
  (s16-layer "SZINES_H\U+00E1tlemez" 17)
  (command "_.COPY" a "" '(0 0 0) '(5100 0 0)) (command "_.CHPROP" (entlast) "" "_LA" "SZINES_H\U+00E1tlemez" "")
  ;; D1-FRONT
  (s16-layer "$PART_S16_D1-FRONT\U+02D90\U+02D90\U+00A8VVVV\U+02D90\U+00A8#0\U+00A816005" "64,54,46")
  (setq a (s16-box 436.5 -400 171 432 18 378))
  (s16-layer "SZINES_Front" 81)
  (command "_.COPY" a "" '(0 0 0) '(5100 0 0)) (command "_.CHPROP" (entlast) "" "_LA" "SZINES_Front" "")
  ;; D1-BOX-L
  (s16-layer "$PART_S16_D1-BOX-L\U+02D90\U+02D90\U+00A8LLLL\U+02D90\U+00A8#0\U+00A816006" "196,175,139")
  (setq a (s16-box 459 -370 210 15 290 237))
  (s16-layer "SZINES_Fi\U+00F3koldal" 40)
  (command "_.COPY" a "" '(0 0 0) '(5100 0 0)) (command "_.CHPROP" (entlast) "" "_LA" "SZINES_Fi\U+00F3koldal" "")
  ;; D1-BOX-R
  (s16-layer "$PART_S16_D1-BOX-R\U+02D90\U+02D90\U+00A8LLLL\U+02D90\U+00A8#0\U+00A816007" "196,175,139")
  (setq a (s16-box 831 -370 210 15 290 237))
  (s16-layer "SZINES_Fi\U+00F3koldal" 40)
  (command "_.COPY" a "" '(0 0 0) '(5100 0 0)) (command "_.CHPROP" (entlast) "" "_LA" "SZINES_Fi\U+00F3koldal" "")
  ;; D1-BOX-F
  (s16-layer "$PART_S16_D1-BOX-F\U+02D90\U+02D90\U+00A8L000\U+02D90\U+00A8#0\U+00A816008" "196,175,139")
  (setq a (s16-box 474 -370 237 357 15 210))
  (s16-layer "SZINES_Fi\U+00F3kh\U+00E1t" 55)
  (command "_.COPY" a "" '(0 0 0) '(5100 0 0)) (command "_.CHPROP" (entlast) "" "_LA" "SZINES_Fi\U+00F3kh\U+00E1t" "")
  ;; D1-BOX-H
  (s16-layer "$PART_S16_D1-BOX-H\U+02D90\U+02D90\U+00A8L000\U+02D90\U+00A8#0\U+00A816009" "196,175,139")
  (setq a (s16-box 474 -95 237 357 15 210))
  (s16-layer "SZINES_Fi\U+00F3kh\U+00E1t" 55)
  (command "_.COPY" a "" '(0 0 0) '(5100 0 0)) (command "_.CHPROP" (entlast) "" "_LA" "SZINES_Fi\U+00F3kh\U+00E1t" "")
  ;; D1-BOX-B
  (s16-layer "$PART_S16_D1-BOX-B\U+02D90\U+02D90\U+00A8LL00\U+02D90\U+00A8#0\U+00A816010" "196,175,139")
  (setq a (s16-box 474 -370 222 357 290 15))
  (s16-layer "SZINES_Fi\U+00F3kfen\U+00E9k" 65)
  (command "_.COPY" a "" '(0 0 0) '(5100 0 0)) (command "_.CHPROP" (entlast) "" "_LA" "SZINES_Fi\U+00F3kfen\U+00E9k" "")
  ;; D2-L
  (s16-layer "$PART_S16_D2-L\U+02D90\U+02D90\U+00A8V0VV\U+02D90\U+00A8#0\U+00A816011" "80,73,66")
  (setq a (s16-box 870 -377 150 18 337 420))
  (s16-layer "SZINES_Oldal" 40)
  (command "_.COPY" a "" '(0 0 0) '(5100 0 0)) (command "_.CHPROP" (entlast) "" "_LA" "SZINES_Oldal" "")
  ;; D2-R
  (s16-layer "$PART_S16_D2-R\U+02D90\U+02D90\U+00A8V0VV\U+02D90\U+00A8#0\U+00A816012" "80,73,66")
  (setq a (s16-box 1277 -377 150 18 337 420))
  (s16-layer "SZINES_Oldal" 40)
  (command "_.COPY" a "" '(0 0 0) '(5100 0 0)) (command "_.CHPROP" (entlast) "" "_LA" "SZINES_Oldal" "")
  ;; D2-B
  (s16-layer "$PART_S16_D2-B\U+02D90\U+02D90\U+00A8V000\U+02D90\U+00A8#0\U+00A816013" "80,73,66")
  (setq a (s16-box 888 -377 150 389 337 18))
  (s16-layer "SZINES_Tet\U+0151" 173)
  (command "_.COPY" a "" '(0 0 0) '(5100 0 0)) (command "_.CHPROP" (entlast) "" "_LA" "SZINES_Tet\U+0151" "")
  ;; D2-T
  (s16-layer "$PART_S16_D2-T\U+02D90\U+02D90\U+00A8FF00\U+02D90\U+00A8#0\U+00A816014" "51,44,38")
  (setq a (s16-box 888 -377 552 389 337 18))
  (s16-layer "SZINES_Tet\U+0151" 173)
  (command "_.COPY" a "" '(0 0 0) '(5100 0 0)) (command "_.CHPROP" (entlast) "" "_LA" "SZINES_Tet\U+0151" "")
  ;; D2-BACK
  (s16-layer "$PART_S16_D2-BACK\U+02D90\U+02D90\U+00A80000\U+02D90\U+00A8#0\U+00A816015" "105,108,103")
  (setq a (s16-box 888 -48 168 389 8 384))
  (s16-layer "SZINES_H\U+00E1tlemez" 17)
  (command "_.COPY" a "" '(0 0 0) '(5100 0 0)) (command "_.CHPROP" (entlast) "" "_LA" "SZINES_H\U+00E1tlemez" "")
  ;; D2-FRONT
  (s16-layer "$PART_S16_D2-FRONT\U+02D90\U+02D90\U+00A8VVVV\U+02D90\U+00A8#0\U+00A816016" "64,54,46")
  (setq a (s16-box 871.5 -400 171 422 18 378))
  (s16-layer "SZINES_Front" 81)
  (command "_.COPY" a "" '(0 0 0) '(5100 0 0)) (command "_.CHPROP" (entlast) "" "_LA" "SZINES_Front" "")
  ;; D2-BOX-L
  (s16-layer "$PART_S16_D2-BOX-L\U+02D90\U+02D90\U+00A8LLLL\U+02D90\U+00A8#0\U+00A816017" "196,175,139")
  (setq a (s16-box 894 -370 210 15 290 237))
  (s16-layer "SZINES_Fi\U+00F3koldal" 40)
  (command "_.COPY" a "" '(0 0 0) '(5100 0 0)) (command "_.CHPROP" (entlast) "" "_LA" "SZINES_Fi\U+00F3koldal" "")
  ;; D2-BOX-R
  (s16-layer "$PART_S16_D2-BOX-R\U+02D90\U+02D90\U+00A8LLLL\U+02D90\U+00A8#0\U+00A816018" "196,175,139")
  (setq a (s16-box 1256 -370 210 15 290 237))
  (s16-layer "SZINES_Fi\U+00F3koldal" 40)
  (command "_.COPY" a "" '(0 0 0) '(5100 0 0)) (command "_.CHPROP" (entlast) "" "_LA" "SZINES_Fi\U+00F3koldal" "")
  ;; D2-BOX-F
  (s16-layer "$PART_S16_D2-BOX-F\U+02D90\U+02D90\U+00A8L000\U+02D90\U+00A8#0\U+00A816019" "196,175,139")
  (setq a (s16-box 909 -370 237 347 15 210))
  (s16-layer "SZINES_Fi\U+00F3kh\U+00E1t" 55)
  (command "_.COPY" a "" '(0 0 0) '(5100 0 0)) (command "_.CHPROP" (entlast) "" "_LA" "SZINES_Fi\U+00F3kh\U+00E1t" "")
  ;; D2-BOX-H
  (s16-layer "$PART_S16_D2-BOX-H\U+02D90\U+02D90\U+00A8L000\U+02D90\U+00A8#0\U+00A816020" "196,175,139")
  (setq a (s16-box 909 -95 237 347 15 210))
  (s16-layer "SZINES_Fi\U+00F3kh\U+00E1t" 55)
  (command "_.COPY" a "" '(0 0 0) '(5100 0 0)) (command "_.CHPROP" (entlast) "" "_LA" "SZINES_Fi\U+00F3kh\U+00E1t" "")
  ;; D2-BOX-B
  (s16-layer "$PART_S16_D2-BOX-B\U+02D90\U+02D90\U+00A8LL00\U+02D90\U+00A8#0\U+00A816021" "196,175,139")
  (setq a (s16-box 909 -370 222 347 290 15))
  (s16-layer "SZINES_Fi\U+00F3kfen\U+00E9k" 65)
  (command "_.COPY" a "" '(0 0 0) '(5100 0 0)) (command "_.CHPROP" (entlast) "" "_LA" "SZINES_Fi\U+00F3kfen\U+00E9k" "")
  ;; D3-L
  (s16-layer "$PART_S16_D3-L\U+02D90\U+02D90\U+00A8V0VV\U+02D90\U+00A8#0\U+00A816022" "80,73,66")
  (setq a (s16-box 1295 -377 150 18 337 420))
  (s16-layer "SZINES_Oldal" 40)
  (command "_.COPY" a "" '(0 0 0) '(5100 0 0)) (command "_.CHPROP" (entlast) "" "_LA" "SZINES_Oldal" "")
  ;; D3-R
  (s16-layer "$PART_S16_D3-R\U+02D90\U+02D90\U+00A8V0VV\U+02D90\U+00A8#0\U+00A816023" "80,73,66")
  (setq a (s16-box 1702 -377 150 18 337 420))
  (s16-layer "SZINES_Oldal" 40)
  (command "_.COPY" a "" '(0 0 0) '(5100 0 0)) (command "_.CHPROP" (entlast) "" "_LA" "SZINES_Oldal" "")
  ;; D3-B
  (s16-layer "$PART_S16_D3-B\U+02D90\U+02D90\U+00A8V000\U+02D90\U+00A8#0\U+00A816024" "80,73,66")
  (setq a (s16-box 1313 -377 150 389 337 18))
  (s16-layer "SZINES_Tet\U+0151" 173)
  (command "_.COPY" a "" '(0 0 0) '(5100 0 0)) (command "_.CHPROP" (entlast) "" "_LA" "SZINES_Tet\U+0151" "")
  ;; D3-T
  (s16-layer "$PART_S16_D3-T\U+02D90\U+02D90\U+00A8FF00\U+02D90\U+00A8#0\U+00A816025" "51,44,38")
  (setq a (s16-box 1313 -377 552 389 337 18))
  (s16-layer "SZINES_Tet\U+0151" 173)
  (command "_.COPY" a "" '(0 0 0) '(5100 0 0)) (command "_.CHPROP" (entlast) "" "_LA" "SZINES_Tet\U+0151" "")
  ;; D3-BACK
  (s16-layer "$PART_S16_D3-BACK\U+02D90\U+02D90\U+00A80000\U+02D90\U+00A8#0\U+00A816026" "105,108,103")
  (setq a (s16-box 1313 -48 168 389 8 384))
  (s16-layer "SZINES_H\U+00E1tlemez" 17)
  (command "_.COPY" a "" '(0 0 0) '(5100 0 0)) (command "_.CHPROP" (entlast) "" "_LA" "SZINES_H\U+00E1tlemez" "")
  ;; D3-FRONT
  (s16-layer "$PART_S16_D3-FRONT\U+02D90\U+02D90\U+00A8VVVV\U+02D90\U+00A8#0\U+00A816027" "64,54,46")
  (setq a (s16-box 1296.5 -400 171 422 18 378))
  (s16-layer "SZINES_Front" 81)
  (command "_.COPY" a "" '(0 0 0) '(5100 0 0)) (command "_.CHPROP" (entlast) "" "_LA" "SZINES_Front" "")
  ;; D3-BOX-L
  (s16-layer "$PART_S16_D3-BOX-L\U+02D90\U+02D90\U+00A8LLLL\U+02D90\U+00A8#0\U+00A816028" "196,175,139")
  (setq a (s16-box 1319 -370 210 15 290 237))
  (s16-layer "SZINES_Fi\U+00F3koldal" 40)
  (command "_.COPY" a "" '(0 0 0) '(5100 0 0)) (command "_.CHPROP" (entlast) "" "_LA" "SZINES_Fi\U+00F3koldal" "")
  ;; D3-BOX-R
  (s16-layer "$PART_S16_D3-BOX-R\U+02D90\U+02D90\U+00A8LLLL\U+02D90\U+00A8#0\U+00A816029" "196,175,139")
  (setq a (s16-box 1681 -370 210 15 290 237))
  (s16-layer "SZINES_Fi\U+00F3koldal" 40)
  (command "_.COPY" a "" '(0 0 0) '(5100 0 0)) (command "_.CHPROP" (entlast) "" "_LA" "SZINES_Fi\U+00F3koldal" "")
  ;; D3-BOX-F
  (s16-layer "$PART_S16_D3-BOX-F\U+02D90\U+02D90\U+00A8L000\U+02D90\U+00A8#0\U+00A816030" "196,175,139")
  (setq a (s16-box 1334 -370 237 347 15 210))
  (s16-layer "SZINES_Fi\U+00F3kh\U+00E1t" 55)
  (command "_.COPY" a "" '(0 0 0) '(5100 0 0)) (command "_.CHPROP" (entlast) "" "_LA" "SZINES_Fi\U+00F3kh\U+00E1t" "")
  ;; D3-BOX-H
  (s16-layer "$PART_S16_D3-BOX-H\U+02D90\U+02D90\U+00A8L000\U+02D90\U+00A8#0\U+00A816031" "196,175,139")
  (setq a (s16-box 1334 -95 237 347 15 210))
  (s16-layer "SZINES_Fi\U+00F3kh\U+00E1t" 55)
  (command "_.COPY" a "" '(0 0 0) '(5100 0 0)) (command "_.CHPROP" (entlast) "" "_LA" "SZINES_Fi\U+00F3kh\U+00E1t" "")
  ;; D3-BOX-B
  (s16-layer "$PART_S16_D3-BOX-B\U+02D90\U+02D90\U+00A8LL00\U+02D90\U+00A8#0\U+00A816032" "196,175,139")
  (setq a (s16-box 1334 -370 222 347 290 15))
  (s16-layer "SZINES_Fi\U+00F3kfen\U+00E9k" 65)
  (command "_.COPY" a "" '(0 0 0) '(5100 0 0)) (command "_.CHPROP" (entlast) "" "_LA" "SZINES_Fi\U+00F3kfen\U+00E9k" "")
  ;; D4-L
  (s16-layer "$PART_S16_D4-L\U+02D90\U+02D90\U+00A8V0VV\U+02D90\U+00A8#0\U+00A816033" "80,73,66")
  (setq a (s16-box 1720 -377 150 18 337 420))
  (s16-layer "SZINES_Oldal" 40)
  (command "_.COPY" a "" '(0 0 0) '(5100 0 0)) (command "_.CHPROP" (entlast) "" "_LA" "SZINES_Oldal" "")
  ;; D4-R
  (s16-layer "$PART_S16_D4-R\U+02D90\U+02D90\U+00A8V0VV\U+02D90\U+00A8#0\U+00A816034" "80,73,66")
  (setq a (s16-box 2732 -377 150 18 337 420))
  (s16-layer "SZINES_Oldal" 40)
  (command "_.COPY" a "" '(0 0 0) '(5100 0 0)) (command "_.CHPROP" (entlast) "" "_LA" "SZINES_Oldal" "")
  ;; D4-B
  (s16-layer "$PART_S16_D4-B\U+02D90\U+02D90\U+00A8V000\U+02D90\U+00A8#0\U+00A816035" "80,73,66")
  (setq a (s16-box 1738 -377 150 994 337 18))
  (s16-layer "SZINES_Tet\U+0151" 173)
  (command "_.COPY" a "" '(0 0 0) '(5100 0 0)) (command "_.CHPROP" (entlast) "" "_LA" "SZINES_Tet\U+0151" "")
  ;; D4-T
  (s16-layer "$PART_S16_D4-T\U+02D90\U+02D90\U+00A8FF00\U+02D90\U+00A8#0\U+00A816036" "51,44,38")
  (setq a (s16-box 1738 -377 552 994 337 18))
  (s16-layer "SZINES_Tet\U+0151" 173)
  (command "_.COPY" a "" '(0 0 0) '(5100 0 0)) (command "_.CHPROP" (entlast) "" "_LA" "SZINES_Tet\U+0151" "")
  ;; D4-BACK
  (s16-layer "$PART_S16_D4-BACK\U+02D90\U+02D90\U+00A80000\U+02D90\U+00A8#0\U+00A816037" "105,108,103")
  (setq a (s16-box 1738 -48 168 994 8 384))
  (s16-layer "SZINES_H\U+00E1tlemez" 17)
  (command "_.COPY" a "" '(0 0 0) '(5100 0 0)) (command "_.CHPROP" (entlast) "" "_LA" "SZINES_H\U+00E1tlemez" "")
  ;; D4-FRONT
  (s16-layer "$PART_S16_D4-FRONT\U+02D90\U+02D90\U+00A8VVVV\U+02D90\U+00A8#0\U+00A816038" "64,54,46")
  (setq a (s16-box 1721.5 -400 171 1027 18 378))
  (s16-layer "SZINES_Front" 81)
  (command "_.COPY" a "" '(0 0 0) '(5100 0 0)) (command "_.CHPROP" (entlast) "" "_LA" "SZINES_Front" "")
  ;; D4-BOX-L
  (s16-layer "$PART_S16_D4-BOX-L\U+02D90\U+02D90\U+00A8LLLL\U+02D90\U+00A8#0\U+00A816039" "196,175,139")
  (setq a (s16-box 1744 -370 210 15 290 237))
  (s16-layer "SZINES_Fi\U+00F3koldal" 40)
  (command "_.COPY" a "" '(0 0 0) '(5100 0 0)) (command "_.CHPROP" (entlast) "" "_LA" "SZINES_Fi\U+00F3koldal" "")
  ;; D4-BOX-R
  (s16-layer "$PART_S16_D4-BOX-R\U+02D90\U+02D90\U+00A8LLLL\U+02D90\U+00A8#0\U+00A816040" "196,175,139")
  (setq a (s16-box 2711 -370 210 15 290 237))
  (s16-layer "SZINES_Fi\U+00F3koldal" 40)
  (command "_.COPY" a "" '(0 0 0) '(5100 0 0)) (command "_.CHPROP" (entlast) "" "_LA" "SZINES_Fi\U+00F3koldal" "")
  ;; D4-BOX-F
  (s16-layer "$PART_S16_D4-BOX-F\U+02D90\U+02D90\U+00A8L000\U+02D90\U+00A8#0\U+00A816041" "196,175,139")
  (setq a (s16-box 1759 -370 237 952 15 210))
  (s16-layer "SZINES_Fi\U+00F3kh\U+00E1t" 55)
  (command "_.COPY" a "" '(0 0 0) '(5100 0 0)) (command "_.CHPROP" (entlast) "" "_LA" "SZINES_Fi\U+00F3kh\U+00E1t" "")
  ;; D4-BOX-H
  (s16-layer "$PART_S16_D4-BOX-H\U+02D90\U+02D90\U+00A8L000\U+02D90\U+00A8#0\U+00A816042" "196,175,139")
  (setq a (s16-box 1759 -95 237 952 15 210))
  (s16-layer "SZINES_Fi\U+00F3kh\U+00E1t" 55)
  (command "_.COPY" a "" '(0 0 0) '(5100 0 0)) (command "_.CHPROP" (entlast) "" "_LA" "SZINES_Fi\U+00F3kh\U+00E1t" "")
  ;; D4-BOX-B
  (s16-layer "$PART_S16_D4-BOX-B\U+02D90\U+02D90\U+00A8LL00\U+02D90\U+00A8#0\U+00A816043" "196,175,139")
  (setq a (s16-box 1759 -370 222 952 290 15))
  (s16-layer "SZINES_Fi\U+00F3kfen\U+00E9k" 65)
  (command "_.COPY" a "" '(0 0 0) '(5100 0 0)) (command "_.CHPROP" (entlast) "" "_LA" "SZINES_Fi\U+00F3kfen\U+00E9k" "")
  ;; D5-L
  (s16-layer "$PART_S16_D5-L\U+02D90\U+02D90\U+00A8V0VV\U+02D90\U+00A8#0\U+00A816044" "80,73,66")
  (setq a (s16-box 2750 -377 150 18 337 420))
  (s16-layer "SZINES_Oldal" 40)
  (command "_.COPY" a "" '(0 0 0) '(5100 0 0)) (command "_.CHPROP" (entlast) "" "_LA" "SZINES_Oldal" "")
  ;; D5-R
  (s16-layer "$PART_S16_D5-R\U+02D90\U+02D90\U+00A8V0VV\U+02D90\U+00A8#0\U+00A816045" "80,73,66")
  (setq a (s16-box 3157 -377 150 18 337 420))
  (s16-layer "SZINES_Oldal" 40)
  (command "_.COPY" a "" '(0 0 0) '(5100 0 0)) (command "_.CHPROP" (entlast) "" "_LA" "SZINES_Oldal" "")
  ;; D5-B
  (s16-layer "$PART_S16_D5-B\U+02D90\U+02D90\U+00A8V000\U+02D90\U+00A8#0\U+00A816046" "80,73,66")
  (setq a (s16-box 2768 -377 150 389 337 18))
  (s16-layer "SZINES_Tet\U+0151" 173)
  (command "_.COPY" a "" '(0 0 0) '(5100 0 0)) (command "_.CHPROP" (entlast) "" "_LA" "SZINES_Tet\U+0151" "")
  ;; D5-T
  (s16-layer "$PART_S16_D5-T\U+02D90\U+02D90\U+00A8FF00\U+02D90\U+00A8#0\U+00A816047" "51,44,38")
  (setq a (s16-box 2768 -377 552 389 337 18))
  (s16-layer "SZINES_Tet\U+0151" 173)
  (command "_.COPY" a "" '(0 0 0) '(5100 0 0)) (command "_.CHPROP" (entlast) "" "_LA" "SZINES_Tet\U+0151" "")
  ;; D5-BACK
  (s16-layer "$PART_S16_D5-BACK\U+02D90\U+02D90\U+00A80000\U+02D90\U+00A8#0\U+00A816048" "105,108,103")
  (setq a (s16-box 2768 -48 168 389 8 384))
  (s16-layer "SZINES_H\U+00E1tlemez" 17)
  (command "_.COPY" a "" '(0 0 0) '(5100 0 0)) (command "_.CHPROP" (entlast) "" "_LA" "SZINES_H\U+00E1tlemez" "")
  ;; D5-FRONT
  (s16-layer "$PART_S16_D5-FRONT\U+02D90\U+02D90\U+00A8VVVV\U+02D90\U+00A8#0\U+00A816049" "64,54,46")
  (setq a (s16-box 2751.5 -400 171 422 18 378))
  (s16-layer "SZINES_Front" 81)
  (command "_.COPY" a "" '(0 0 0) '(5100 0 0)) (command "_.CHPROP" (entlast) "" "_LA" "SZINES_Front" "")
  ;; D5-BOX-L
  (s16-layer "$PART_S16_D5-BOX-L\U+02D90\U+02D90\U+00A8LLLL\U+02D90\U+00A8#0\U+00A816050" "196,175,139")
  (setq a (s16-box 2774 -370 210 15 290 237))
  (s16-layer "SZINES_Fi\U+00F3koldal" 40)
  (command "_.COPY" a "" '(0 0 0) '(5100 0 0)) (command "_.CHPROP" (entlast) "" "_LA" "SZINES_Fi\U+00F3koldal" "")
  ;; D5-BOX-R
  (s16-layer "$PART_S16_D5-BOX-R\U+02D90\U+02D90\U+00A8LLLL\U+02D90\U+00A8#0\U+00A816051" "196,175,139")
  (setq a (s16-box 3136 -370 210 15 290 237))
  (s16-layer "SZINES_Fi\U+00F3koldal" 40)
  (command "_.COPY" a "" '(0 0 0) '(5100 0 0)) (command "_.CHPROP" (entlast) "" "_LA" "SZINES_Fi\U+00F3koldal" "")
  ;; D5-BOX-F
  (s16-layer "$PART_S16_D5-BOX-F\U+02D90\U+02D90\U+00A8L000\U+02D90\U+00A8#0\U+00A816052" "196,175,139")
  (setq a (s16-box 2789 -370 237 347 15 210))
  (s16-layer "SZINES_Fi\U+00F3kh\U+00E1t" 55)
  (command "_.COPY" a "" '(0 0 0) '(5100 0 0)) (command "_.CHPROP" (entlast) "" "_LA" "SZINES_Fi\U+00F3kh\U+00E1t" "")
  ;; D5-BOX-H
  (s16-layer "$PART_S16_D5-BOX-H\U+02D90\U+02D90\U+00A8L000\U+02D90\U+00A8#0\U+00A816053" "196,175,139")
  (setq a (s16-box 2789 -95 237 347 15 210))
  (s16-layer "SZINES_Fi\U+00F3kh\U+00E1t" 55)
  (command "_.COPY" a "" '(0 0 0) '(5100 0 0)) (command "_.CHPROP" (entlast) "" "_LA" "SZINES_Fi\U+00F3kh\U+00E1t" "")
  ;; D5-BOX-B
  (s16-layer "$PART_S16_D5-BOX-B\U+02D90\U+02D90\U+00A8LL00\U+02D90\U+00A8#0\U+00A816054" "196,175,139")
  (setq a (s16-box 2789 -370 222 347 290 15))
  (s16-layer "SZINES_Fi\U+00F3kfen\U+00E9k" 65)
  (command "_.COPY" a "" '(0 0 0) '(5100 0 0)) (command "_.CHPROP" (entlast) "" "_LA" "SZINES_Fi\U+00F3kfen\U+00E9k" "")
  ;; D6-L
  (s16-layer "$PART_S16_D6-L\U+02D90\U+02D90\U+00A8V0VV\U+02D90\U+00A8#0\U+00A816055" "80,73,66")
  (setq a (s16-box 3175 -377 150 18 337 420))
  (s16-layer "SZINES_Oldal" 40)
  (command "_.COPY" a "" '(0 0 0) '(5100 0 0)) (command "_.CHPROP" (entlast) "" "_LA" "SZINES_Oldal" "")
  ;; D6-R
  (s16-layer "$PART_S16_D6-R\U+02D90\U+02D90\U+00A800FF\U+02D90\U+00A8#0\U+00A816056" "51,44,38")
  (setq a (s16-box 3582 -377 230 18 337 260))
  (s16-layer "SZINES_Oldal" 40)
  (command "_.COPY" a "" '(0 0 0) '(5100 0 0)) (command "_.CHPROP" (entlast) "" "_LA" "SZINES_Oldal" "")
  ;; D6-B
  (s16-layer "$PART_S16_D6-B\U+02D90\U+02D90\U+00A800V0\U+02D90\U+00A8#0\U+00A816057" "80,73,66")
  (setq a (s16-box 3193 -377 150 327 337 18))
  (s16-layer "SZINES_Tet\U+0151" 173)
  (command "_.COPY" a "" '(0 0 0) '(5100 0 0)) (command "_.CHPROP" (entlast) "" "_LA" "SZINES_Tet\U+0151" "")
  ;; D6-T
  (s16-layer "$PART_S16_D6-T\U+02D90\U+02D90\U+00A800FF\U+02D90\U+00A8#0\U+00A816058" "51,44,38")
  (setq a (s16-box 3193 -377 552 327 337 18))
  (s16-layer "SZINES_Tet\U+0151" 173)
  (command "_.COPY" a "" '(0 0 0) '(5100 0 0)) (command "_.CHPROP" (entlast) "" "_LA" "SZINES_Tet\U+0151" "")
  ;; D6-BACK
  (s16-layer "$PART_S16_D6-BACK\U+02D90\U+02D90\U+00A80000\U+02D90\U+00A8#0\U+00A816059" "105,108,103")
  (setq s16p nil)
  (setq s16p (append s16p (list (list 0.0000 0.0000 0.000000000) (list 327.0000 0.0000 0.414213562) (list 389.0000 62.0000 0.000000000) (list 389.0000 322.0000 0.414213562) (list 327.0000 384.0000 0.000000000) (list 0.0000 384.0000 0.000000000))))
  (setq a (s16-extrude-y s16p 8 3193 -40 168))
  (s16-layer "SZINES_H\U+00E1tlemez" 17)
  (command "_.COPY" a "" '(0 0 0) '(5100 0 0)) (command "_.CHPROP" (entlast) "" "_LA" "SZINES_H\U+00E1tlemez" "")
  ;; D6-FRONT
  (s16-layer "$PART_S16_D6-FRONT\U+02D90\U+02D90\U+00A8VVVV\U+02D90\U+00A8#0\U+00A816060" "64,54,46")
  (setq s16p nil)
  (setq s16p (append s16p (list (list 0.0000 0.0000 0.000000000) (list 343.5000 0.0000 0.414213562) (list 402.5000 59.0000 0.000000000) (list 402.5000 319.0000 0.414213562) (list 343.5000 378.0000 0.000000000) (list 0.0000 378.0000 0.000000000))))
  (setq a (s16-extrude-y s16p 18 3176.5 -382 171))
  (s16-layer "SZINES_Front" 81)
  (command "_.COPY" a "" '(0 0 0) '(5100 0 0)) (command "_.CHPROP" (entlast) "" "_LA" "SZINES_Front" "")
  ;; D6-BOX-L
  (s16-layer "$PART_S16_D6-BOX-L\U+02D90\U+02D90\U+00A8LLLL\U+02D90\U+00A8#0\U+00A816061" "196,175,139")
  (setq a (s16-box 3199 -370 245.0 15 290 202.0))
  (s16-layer "SZINES_Fi\U+00F3koldal" 40)
  (command "_.COPY" a "" '(0 0 0) '(5100 0 0)) (command "_.CHPROP" (entlast) "" "_LA" "SZINES_Fi\U+00F3koldal" "")
  ;; D6-BOX-R
  (s16-layer "$PART_S16_D6-BOX-R\U+02D90\U+02D90\U+00A8LLLL\U+02D90\U+00A8#0\U+00A816062" "196,175,139")
  (setq a (s16-box 3561 -370 245.0 15 290 202.0))
  (s16-layer "SZINES_Fi\U+00F3koldal" 40)
  (command "_.COPY" a "" '(0 0 0) '(5100 0 0)) (command "_.CHPROP" (entlast) "" "_LA" "SZINES_Fi\U+00F3koldal" "")
  ;; D6-BOX-F
  (s16-layer "$PART_S16_D6-BOX-F\U+02D90\U+02D90\U+00A8L000\U+02D90\U+00A8#0\U+00A816063" "196,175,139")
  (setq a (s16-box 3214 -370 272.0 347 15 175.0))
  (s16-layer "SZINES_Fi\U+00F3kh\U+00E1t" 55)
  (command "_.COPY" a "" '(0 0 0) '(5100 0 0)) (command "_.CHPROP" (entlast) "" "_LA" "SZINES_Fi\U+00F3kh\U+00E1t" "")
  ;; D6-BOX-H
  (s16-layer "$PART_S16_D6-BOX-H\U+02D90\U+02D90\U+00A8L000\U+02D90\U+00A8#0\U+00A816064" "196,175,139")
  (setq a (s16-box 3214 -95 272.0 347 15 175.0))
  (s16-layer "SZINES_Fi\U+00F3kh\U+00E1t" 55)
  (command "_.COPY" a "" '(0 0 0) '(5100 0 0)) (command "_.CHPROP" (entlast) "" "_LA" "SZINES_Fi\U+00F3kh\U+00E1t" "")
  ;; D6-BOX-B
  (s16-layer "$PART_S16_D6-BOX-B\U+02D90\U+02D90\U+00A8LL00\U+02D90\U+00A8#0\U+00A816065" "196,175,139")
  (setq a (s16-box 3214 -370 257.0 347 290 15))
  (s16-layer "SZINES_Fi\U+00F3kfen\U+00E9k" 65)
  (command "_.COPY" a "" '(0 0 0) '(5100 0 0)) (command "_.CHPROP" (entlast) "" "_LA" "SZINES_Fi\U+00F3kfen\U+00E9k" "")
  ;; T-L
  (s16-layer "$PART_S16_T-L\U+02D90\U+02D90\U+00A8V000\U+02D90\U+00A8#0\U+00A816066" "80,73,66")
  (setq a (s16-box 0 -377 250 18 337 2525))
  (s16-layer "SZINES_Oldal" 40)
  (command "_.COPY" a "" '(0 0 0) '(5100 0 0)) (command "_.CHPROP" (entlast) "" "_LA" "SZINES_Oldal" "")
  ;; T-R
  (s16-layer "$PART_S16_T-R\U+02D90\U+02D90\U+00A8FF00\U+02D90\U+00A8#0\U+00A816067" "51,44,38")
  (setq a (s16-box 852 -377 570 18 337 2205))
  (s16-layer "SZINES_Oldal" 40)
  (command "_.COPY" a "" '(0 0 0) '(5100 0 0)) (command "_.CHPROP" (entlast) "" "_LA" "SZINES_Oldal" "")
  ;; T-B
  (s16-layer "$DIFF_OUT" 1)
  (setq b (s16-box 37 -378 569 380 28 20))
  (s16-layer "$PART_S16_T-B\U+02D90\U+02D90\U+00A8V000\U+02D90\U+00A8#0\U+00A816068" "80,73,66")
  (setq a (s16-box 18 -377 570 834 337 18))
  (s16-layer "$PART_S16_T-B\U+02D90\U+02D90\U+00A8V000\U+02D90\U+00A8#0\U+00A816068" "80,73,66")
  (setq b (s16-box 37 -378 569 380 28 20))
  (s16-sub a b)
  (s16-layer "SZINES_Tet\U+0151" 173)
  (command "_.COPY" a "" '(0 0 0) '(5100 0 0)) (command "_.CHPROP" (entlast) "" "_LA" "SZINES_Tet\U+0151" "")
  ;; T-C
  (s16-layer "$PART_S16_T-C\U+02D90\U+02D90\U+00A8V000\U+02D90\U+00A8#0\U+00A816069" "80,73,66")
  (setq a (s16-box 426 -377 588 18 337 2269))
  (s16-layer "SZINES_Voszt\U+00F3" 93)
  (command "_.COPY" a "" '(0 0 0) '(5100 0 0)) (command "_.CHPROP" (entlast) "" "_LA" "SZINES_Voszt\U+00F3" "")
  ;; T-L-S1
  (s16-layer "$PART_S16_T-L-S1\U+02D90\U+02D90\U+00A8V000\U+02D90\U+00A8#0\U+00A816070" "80,73,66")
  (setq a (s16-box 19 -340 935 406 290 18))
  (s16-layer "SZINES_Polc" 145)
  (command "_.COPY" a "" '(0 0 0) '(5100 0 0)) (command "_.CHPROP" (entlast) "" "_LA" "SZINES_Polc" "")
  ;; T-L-S2
  (s16-layer "$PART_S16_T-L-S2\U+02D90\U+02D90\U+00A8V000\U+02D90\U+00A8#0\U+00A816071" "80,73,66")
  (setq a (s16-box 19 -340 1320 406 290 18))
  (s16-layer "SZINES_Polc" 145)
  (command "_.COPY" a "" '(0 0 0) '(5100 0 0)) (command "_.CHPROP" (entlast) "" "_LA" "SZINES_Polc" "")
  ;; T-L-S3
  (s16-layer "$PART_S16_T-L-S3\U+02D90\U+02D90\U+00A8V000\U+02D90\U+00A8#0\U+00A816072" "80,73,66")
  (setq a (s16-box 19 -340 1705 406 290 18))
  (s16-layer "SZINES_Polc" 145)
  (command "_.COPY" a "" '(0 0 0) '(5100 0 0)) (command "_.CHPROP" (entlast) "" "_LA" "SZINES_Polc" "")
  ;; T-L-S4
  (s16-layer "$PART_S16_T-L-S4\U+02D90\U+02D90\U+00A8V000\U+02D90\U+00A8#0\U+00A816073" "80,73,66")
  (setq a (s16-box 19 -340 2090 406 290 18))
  (s16-layer "SZINES_Polc" 145)
  (command "_.COPY" a "" '(0 0 0) '(5100 0 0)) (command "_.CHPROP" (entlast) "" "_LA" "SZINES_Polc" "")
  ;; T-L-S5
  (s16-layer "$PART_S16_T-L-S5\U+02D90\U+02D90\U+00A8V000\U+02D90\U+00A8#0\U+00A816074" "80,73,66")
  (setq a (s16-box 19 -340 2475 406 290 18))
  (s16-layer "SZINES_Polc" 145)
  (command "_.COPY" a "" '(0 0 0) '(5100 0 0)) (command "_.CHPROP" (entlast) "" "_LA" "SZINES_Polc" "")
  ;; T-L-BACK
  (s16-layer "$PART_S16_T-L-BACK\U+02D90\U+02D90\U+00A80000\U+02D90\U+00A8#0\U+00A816075" "105,108,103")
  (setq s16p nil)
  (setq s16p (append s16p (list (list 0.0000 0.0000 0.000000000) (list 406.0000 0.0000 0.000000000) (list 406.0000 1921.0000 0.000000000) (list 81.0000 1921.0000 0.357805721) (list 0.5756 1854.9974 0.000000000) (list 0.0000 1851.6801 0.000000000))))
  (setq a (s16-extrude-y s16p 8 19 -40 935))
  (s16-layer "SZINES_H\U+00E1tlemez" 17)
  (command "_.COPY" a "" '(0 0 0) '(5100 0 0)) (command "_.CHPROP" (entlast) "" "_LA" "SZINES_H\U+00E1tlemez" "")
  ;; T-L-SERVICE
  (s16-layer "$PART_S16_T-L-SERVICE\U+02D90\U+02D90\U+00A8VVVV\U+02D90\U+00A8#0\U+00A816076" "105,108,103")
  (setq a (s16-box 19 -135 589 406 8 345))
  (s16-layer "SZINES_H\U+00E1tlemez" 17)
  (command "_.COPY" a "" '(0 0 0) '(5100 0 0)) (command "_.CHPROP" (entlast) "" "_LA" "SZINES_H\U+00E1tlemez" "")
  ;; T-R-S1
  (s16-layer "$PART_S16_T-R-S1\U+02D90\U+02D90\U+00A8V000\U+02D90\U+00A8#0\U+00A816077" "80,73,66")
  (setq a (s16-box 445 -340 935 406 290 18))
  (s16-layer "SZINES_Polc" 145)
  (command "_.COPY" a "" '(0 0 0) '(5100 0 0)) (command "_.CHPROP" (entlast) "" "_LA" "SZINES_Polc" "")
  ;; T-R-S2
  (s16-layer "$PART_S16_T-R-S2\U+02D90\U+02D90\U+00A8V000\U+02D90\U+00A8#0\U+00A816078" "80,73,66")
  (setq a (s16-box 445 -340 1320 406 290 18))
  (s16-layer "SZINES_Polc" 145)
  (command "_.COPY" a "" '(0 0 0) '(5100 0 0)) (command "_.CHPROP" (entlast) "" "_LA" "SZINES_Polc" "")
  ;; T-R-S3
  (s16-layer "$PART_S16_T-R-S3\U+02D90\U+02D90\U+00A8V000\U+02D90\U+00A8#0\U+00A816079" "80,73,66")
  (setq a (s16-box 445 -340 1705 406 290 18))
  (s16-layer "SZINES_Polc" 145)
  (command "_.COPY" a "" '(0 0 0) '(5100 0 0)) (command "_.CHPROP" (entlast) "" "_LA" "SZINES_Polc" "")
  ;; T-R-S4
  (s16-layer "$PART_S16_T-R-S4\U+02D90\U+02D90\U+00A8V000\U+02D90\U+00A8#0\U+00A816080" "80,73,66")
  (setq a (s16-box 445 -340 2090 406 290 18))
  (s16-layer "SZINES_Polc" 145)
  (command "_.COPY" a "" '(0 0 0) '(5100 0 0)) (command "_.CHPROP" (entlast) "" "_LA" "SZINES_Polc" "")
  ;; T-R-S5
  (s16-layer "$PART_S16_T-R-S5\U+02D90\U+02D90\U+00A8V000\U+02D90\U+00A8#0\U+00A816081" "80,73,66")
  (setq a (s16-box 445 -340 2475 406 290 18))
  (s16-layer "SZINES_Polc" 145)
  (command "_.COPY" a "" '(0 0 0) '(5100 0 0)) (command "_.CHPROP" (entlast) "" "_LA" "SZINES_Polc" "")
  ;; T-R-BACK
  (s16-layer "$PART_S16_T-R-BACK\U+02D90\U+02D90\U+00A80000\U+02D90\U+00A8#0\U+00A816082" "105,108,103")
  (setq s16p nil)
  (setq s16p (append s16p (list (list 0.0000 0.0000 0.000000000) (list 406.0000 0.0000 0.000000000) (list 406.0000 1851.6801 0.000000000) (list 405.4244 1854.9974 0.357805721) (list 325.0000 1921.0000 0.000000000) (list 0.0000 1921.0000 0.000000000))))
  (setq a (s16-extrude-y s16p 8 445 -40 935))
  (s16-layer "SZINES_H\U+00E1tlemez" 17)
  (command "_.COPY" a "" '(0 0 0) '(5100 0 0)) (command "_.CHPROP" (entlast) "" "_LA" "SZINES_H\U+00E1tlemez" "")
  ;; T-R-SERVICE
  (s16-layer "$PART_S16_T-R-SERVICE\U+02D90\U+02D90\U+00A8VVVV\U+02D90\U+00A8#0\U+00A816083" "105,108,103")
  (setq a (s16-box 445 -135 589 406 8 345))
  (s16-layer "SZINES_H\U+00E1tlemez" 17)
  (command "_.COPY" a "" '(0 0 0) '(5100 0 0)) (command "_.CHPROP" (entlast) "" "_LA" "SZINES_H\U+00E1tlemez" "")
  ;; T-DOOR-L
  (s16-layer "$DIFF_OUT" 1)
  (setq s16p nil)
  (setq s16p (append s16p (list (list 307.5000 89.0000 0.000000000) (list 310.1987 89.0662 0.000000000) (list 312.8909 89.2648 0.000000000) (list 315.5702 89.5953 0.000000000) (list 318.2300 90.0568 0.000000000) (list 320.8639 90.6483 0.000000000) (list 323.4657 91.3683 0.000000000) (list 326.0289 92.2151 0.000000000) (list 328.5476 93.1866 0.000000000) (list 331.0155 94.2806 0.000000000) (list 333.4268 95.4943 0.000000000) (list 335.7757 96.8249 0.000000000) (list 338.0564 98.2692 0.000000000) (list 340.2635 99.8236 0.000000000) (list 342.3916 101.4844 0.000000000) (list 344.4357 103.2477 0.000000000) (list 346.3909 105.1091 0.000000000) (list 348.2523 107.0643 0.000000000) (list 350.0156 109.1084 0.000000000) (list 351.6764 111.2365 0.000000000) (list 353.2308 113.4436 0.000000000) (list 354.6751 115.7243 0.000000000) (list 356.0057 118.0732 0.000000000) (list 357.2194 120.4845 0.000000000) (list 358.3134 122.9524 0.000000000) (list 359.2849 125.4711 0.000000000) (list 360.1317 128.0343 0.000000000) (list 360.8517 130.6361 0.000000000) (list 361.4432 133.2700 0.000000000) (list 361.9047 135.9298 0.000000000) (list 362.2352 138.6091 0.000000000) (list 362.4338 141.3013 0.000000000) (list 362.5000 144.0000 0.000000000) (list 362.5000 2539.0000 0.000000000) (list 362.4338 2541.6987 0.000000000) (list 362.2352 2544.3909 0.000000000) (list 361.9047 2547.0702 0.000000000) (list 361.4432 2549.7300 0.000000000) (list 360.8517 2552.3639 0.000000000) (list 360.1317 2554.9657 0.000000000))))
  (setq s16p (append s16p (list (list 359.2849 2557.5289 0.000000000) (list 358.3134 2560.0476 0.000000000) (list 357.2194 2562.5155 0.000000000) (list 356.0057 2564.9268 0.000000000) (list 354.6751 2567.2757 0.000000000) (list 353.2308 2569.5564 0.000000000) (list 351.6764 2571.7635 0.000000000) (list 350.0156 2573.8916 0.000000000) (list 348.2523 2575.9357 0.000000000) (list 346.3909 2577.8909 0.000000000) (list 344.4357 2579.7523 0.000000000) (list 342.3916 2581.5156 0.000000000) (list 340.2635 2583.1764 0.000000000) (list 338.0564 2584.7308 0.000000000) (list 335.7757 2586.1751 0.000000000) (list 333.4268 2587.5057 0.000000000) (list 331.0155 2588.7194 0.000000000) (list 328.5476 2589.8134 0.000000000) (list 326.0289 2590.7849 0.000000000) (list 323.4657 2591.6317 0.000000000) (list 320.8639 2592.3517 0.000000000) (list 318.2300 2592.9432 0.000000000) (list 315.5702 2593.4047 0.000000000) (list 312.8909 2593.7352 0.000000000) (list 310.1987 2593.9338 0.000000000) (list 307.5000 2594.0000 0.000000000) (list 105.0000 2594.0000 0.000000000) (list 102.3013 2593.9338 0.000000000) (list 99.6091 2593.7352 0.000000000) (list 96.9298 2593.4047 0.000000000) (list 94.2700 2592.9432 0.000000000) (list 91.6361 2592.3517 0.000000000) (list 89.0343 2591.6317 0.000000000) (list 86.4711 2590.7849 0.000000000) (list 83.9524 2589.8134 0.000000000) (list 81.4845 2588.7194 0.000000000) (list 79.0732 2587.5057 0.000000000) (list 76.7243 2586.1751 0.000000000) (list 74.4436 2584.7308 0.000000000) (list 72.2365 2583.1764 0.000000000))))
  (setq s16p (append s16p (list (list 70.1084 2581.5156 0.000000000) (list 68.0643 2579.7523 0.000000000) (list 66.1091 2577.8909 0.000000000) (list 64.2477 2575.9357 0.000000000) (list 62.4844 2573.8916 0.000000000) (list 60.8236 2571.7635 0.000000000) (list 59.2692 2569.5564 0.000000000) (list 57.8249 2567.2757 0.000000000) (list 56.4943 2564.9268 0.000000000) (list 55.2806 2562.5155 0.000000000) (list 54.1866 2560.0476 0.000000000) (list 53.2151 2557.5289 0.000000000) (list 52.3683 2554.9657 0.000000000) (list 51.6483 2552.3639 0.000000000) (list 51.0568 2549.7300 0.000000000) (list 50.5953 2547.0702 0.000000000) (list 50.2648 2544.3909 0.000000000) (list 50.0662 2541.6987 0.000000000) (list 50.0000 2539.0000 0.000000000) (list 50.0000 144.0000 0.000000000) (list 50.0662 141.3013 0.000000000) (list 50.2648 138.6091 0.000000000) (list 50.5953 135.9298 0.000000000) (list 51.0568 133.2700 0.000000000) (list 51.6483 130.6361 0.000000000) (list 52.3683 128.0343 0.000000000) (list 53.2151 125.4711 0.000000000) (list 54.1866 122.9524 0.000000000) (list 55.2806 120.4845 0.000000000) (list 56.4943 118.0732 0.000000000) (list 57.8249 115.7243 0.000000000) (list 59.2692 113.4436 0.000000000) (list 60.8236 111.2365 0.000000000) (list 62.4844 109.1084 0.000000000) (list 64.2477 107.0643 0.000000000) (list 66.1091 105.1091 0.000000000) (list 68.0643 103.2477 0.000000000) (list 70.1084 101.4844 0.000000000) (list 72.2365 99.8236 0.000000000) (list 74.4436 98.2692 0.000000000))))
  (setq s16p (append s16p (list (list 76.7243 96.8249 0.000000000) (list 79.0732 95.4943 0.000000000) (list 81.4845 94.2806 0.000000000) (list 83.9524 93.1866 0.000000000) (list 86.4711 92.2151 0.000000000) (list 89.0343 91.3683 0.000000000) (list 91.6361 90.6483 0.000000000) (list 94.2700 90.0568 0.000000000) (list 96.9298 89.5953 0.000000000) (list 99.6091 89.2648 0.000000000) (list 102.3013 89.0662 0.000000000) (list 105.0000 89.0000 0.000000000))))
  (setq b (s16-extrude-y s16p 20 21 -381 171))
  (s16-layer "$DIFF_OUT" 1)
  (setq s16p nil)
  (setq s16p (append s16p (list (list 307.5000 83.0000 0.000000000) (list 310.4931 83.0735 0.000000000) (list 313.4790 83.2937 0.000000000) (list 316.4506 83.6602 0.000000000) (list 319.4005 84.1721 0.000000000) (list 322.3218 84.8281 0.000000000) (list 325.2074 85.6266 0.000000000) (list 328.0503 86.5658 0.000000000) (list 330.8437 87.6433 0.000000000) (list 333.5809 88.8567 0.000000000) (list 336.2552 90.2028 0.000000000) (list 338.8603 91.6786 0.000000000) (list 341.3898 93.2804 0.000000000) (list 343.8377 95.0043 0.000000000) (list 346.1980 96.8464 0.000000000) (list 348.4651 98.8020 0.000000000) (list 350.6335 100.8665 0.000000000) (list 352.6980 103.0349 0.000000000) (list 354.6536 105.3020 0.000000000) (list 356.4957 107.6623 0.000000000) (list 358.2196 110.1102 0.000000000) (list 359.8214 112.6397 0.000000000) (list 361.2972 115.2448 0.000000000) (list 362.6433 117.9191 0.000000000) (list 363.8567 120.6563 0.000000000) (list 364.9342 123.4497 0.000000000) (list 365.8734 126.2926 0.000000000) (list 366.6719 129.1782 0.000000000) (list 367.3279 132.0995 0.000000000) (list 367.8398 135.0494 0.000000000) (list 368.2063 138.0210 0.000000000) (list 368.4265 141.0069 0.000000000) (list 368.5000 144.0000 0.000000000) (list 368.5000 2539.0000 0.000000000) (list 368.4265 2541.9931 0.000000000) (list 368.2063 2544.9790 0.000000000) (list 367.8398 2547.9506 0.000000000) (list 367.3279 2550.9005 0.000000000) (list 366.6719 2553.8218 0.000000000) (list 365.8734 2556.7074 0.000000000))))
  (setq s16p (append s16p (list (list 364.9342 2559.5503 0.000000000) (list 363.8567 2562.3437 0.000000000) (list 362.6433 2565.0809 0.000000000) (list 361.2972 2567.7552 0.000000000) (list 359.8214 2570.3603 0.000000000) (list 358.2196 2572.8898 0.000000000) (list 356.4957 2575.3377 0.000000000) (list 354.6536 2577.6980 0.000000000) (list 352.6980 2579.9651 0.000000000) (list 350.6335 2582.1335 0.000000000) (list 348.4651 2584.1980 0.000000000) (list 346.1980 2586.1536 0.000000000) (list 343.8377 2587.9957 0.000000000) (list 341.3898 2589.7196 0.000000000) (list 338.8603 2591.3214 0.000000000) (list 336.2552 2592.7972 0.000000000) (list 333.5809 2594.1433 0.000000000) (list 330.8437 2595.3567 0.000000000) (list 328.0503 2596.4342 0.000000000) (list 325.2074 2597.3734 0.000000000) (list 322.3218 2598.1719 0.000000000) (list 319.4005 2598.8279 0.000000000) (list 316.4506 2599.3398 0.000000000) (list 313.4790 2599.7063 0.000000000) (list 310.4931 2599.9265 0.000000000) (list 307.5000 2600.0000 0.000000000) (list 105.0000 2600.0000 0.000000000) (list 102.0069 2599.9265 0.000000000) (list 99.0210 2599.7063 0.000000000) (list 96.0494 2599.3398 0.000000000) (list 93.0995 2598.8279 0.000000000) (list 90.1782 2598.1719 0.000000000) (list 87.2926 2597.3734 0.000000000) (list 84.4497 2596.4342 0.000000000) (list 81.6563 2595.3567 0.000000000) (list 78.9191 2594.1433 0.000000000) (list 76.2448 2592.7972 0.000000000) (list 73.6397 2591.3214 0.000000000) (list 71.1102 2589.7196 0.000000000) (list 68.6623 2587.9957 0.000000000))))
  (setq s16p (append s16p (list (list 66.3020 2586.1536 0.000000000) (list 64.0349 2584.1980 0.000000000) (list 61.8665 2582.1335 0.000000000) (list 59.8020 2579.9651 0.000000000) (list 57.8464 2577.6980 0.000000000) (list 56.0043 2575.3377 0.000000000) (list 54.2804 2572.8898 0.000000000) (list 52.6786 2570.3603 0.000000000) (list 51.2028 2567.7552 0.000000000) (list 49.8567 2565.0809 0.000000000) (list 48.6433 2562.3437 0.000000000) (list 47.5658 2559.5503 0.000000000) (list 46.6266 2556.7074 0.000000000) (list 45.8281 2553.8218 0.000000000) (list 45.1721 2550.9005 0.000000000) (list 44.6602 2547.9506 0.000000000) (list 44.2937 2544.9790 0.000000000) (list 44.0735 2541.9931 0.000000000) (list 44.0000 2539.0000 0.000000000) (list 44.0000 144.0000 0.000000000) (list 44.0735 141.0069 0.000000000) (list 44.2937 138.0210 0.000000000) (list 44.6602 135.0494 0.000000000) (list 45.1721 132.0995 0.000000000) (list 45.8281 129.1782 0.000000000) (list 46.6266 126.2926 0.000000000) (list 47.5658 123.4497 0.000000000) (list 48.6433 120.6563 0.000000000) (list 49.8567 117.9191 0.000000000) (list 51.2028 115.2448 0.000000000) (list 52.6786 112.6397 0.000000000) (list 54.2804 110.1102 0.000000000) (list 56.0043 107.6623 0.000000000) (list 57.8464 105.3020 0.000000000) (list 59.8020 103.0349 0.000000000) (list 61.8665 100.8665 0.000000000) (list 64.0349 98.8020 0.000000000) (list 66.3020 96.8464 0.000000000) (list 68.6623 95.0043 0.000000000) (list 71.1102 93.2804 0.000000000))))
  (setq s16p (append s16p (list (list 73.6397 91.6786 0.000000000) (list 76.2448 90.2028 0.000000000) (list 78.9191 88.8567 0.000000000) (list 81.6563 87.6433 0.000000000) (list 84.4497 86.5658 0.000000000) (list 87.2926 85.6266 0.000000000) (list 90.1782 84.8281 0.000000000) (list 93.0995 84.1721 0.000000000) (list 96.0494 83.6602 0.000000000) (list 99.0210 83.2937 0.000000000) (list 102.0069 83.0735 0.000000000) (list 105.0000 83.0000 0.000000000))))
  (setq b (s16-extrude-y s16p 11 21 -381 171))
  (s16-layer "$PART_S16_T-DOOR-L\U+02D90\U+02D90\U+00A8VVVV\U+02D90\U+00A8#0\U+00A816084" "64,54,46")
  (setq s16p nil)
  (setq s16p (append s16p (list (list 79.0000 0.0000 0.000000000) (list 412.5000 0.0000 0.000000000) (list 412.5000 2683.0000 0.000000000) (list 79.0000 2683.0000 0.414213562) (list 0.0000 2604.0000 0.000000000) (list 0.0000 79.0000 0.414213562))))
  (setq a (s16-extrude-y s16p 18 21 -382 171))
  (s16-layer "$PART_S16_T-DOOR-L\U+02D90\U+02D90\U+00A8VVVV\U+02D90\U+00A8#0\U+00A816084" "64,54,46")
  (setq s16p nil)
  (setq s16p (append s16p (list (list 307.5000 89.0000 0.000000000) (list 310.1987 89.0662 0.000000000) (list 312.8909 89.2648 0.000000000) (list 315.5702 89.5953 0.000000000) (list 318.2300 90.0568 0.000000000) (list 320.8639 90.6483 0.000000000) (list 323.4657 91.3683 0.000000000) (list 326.0289 92.2151 0.000000000) (list 328.5476 93.1866 0.000000000) (list 331.0155 94.2806 0.000000000) (list 333.4268 95.4943 0.000000000) (list 335.7757 96.8249 0.000000000) (list 338.0564 98.2692 0.000000000) (list 340.2635 99.8236 0.000000000) (list 342.3916 101.4844 0.000000000) (list 344.4357 103.2477 0.000000000) (list 346.3909 105.1091 0.000000000) (list 348.2523 107.0643 0.000000000) (list 350.0156 109.1084 0.000000000) (list 351.6764 111.2365 0.000000000) (list 353.2308 113.4436 0.000000000) (list 354.6751 115.7243 0.000000000) (list 356.0057 118.0732 0.000000000) (list 357.2194 120.4845 0.000000000) (list 358.3134 122.9524 0.000000000) (list 359.2849 125.4711 0.000000000) (list 360.1317 128.0343 0.000000000) (list 360.8517 130.6361 0.000000000) (list 361.4432 133.2700 0.000000000) (list 361.9047 135.9298 0.000000000) (list 362.2352 138.6091 0.000000000) (list 362.4338 141.3013 0.000000000) (list 362.5000 144.0000 0.000000000) (list 362.5000 2539.0000 0.000000000) (list 362.4338 2541.6987 0.000000000) (list 362.2352 2544.3909 0.000000000) (list 361.9047 2547.0702 0.000000000) (list 361.4432 2549.7300 0.000000000) (list 360.8517 2552.3639 0.000000000) (list 360.1317 2554.9657 0.000000000))))
  (setq s16p (append s16p (list (list 359.2849 2557.5289 0.000000000) (list 358.3134 2560.0476 0.000000000) (list 357.2194 2562.5155 0.000000000) (list 356.0057 2564.9268 0.000000000) (list 354.6751 2567.2757 0.000000000) (list 353.2308 2569.5564 0.000000000) (list 351.6764 2571.7635 0.000000000) (list 350.0156 2573.8916 0.000000000) (list 348.2523 2575.9357 0.000000000) (list 346.3909 2577.8909 0.000000000) (list 344.4357 2579.7523 0.000000000) (list 342.3916 2581.5156 0.000000000) (list 340.2635 2583.1764 0.000000000) (list 338.0564 2584.7308 0.000000000) (list 335.7757 2586.1751 0.000000000) (list 333.4268 2587.5057 0.000000000) (list 331.0155 2588.7194 0.000000000) (list 328.5476 2589.8134 0.000000000) (list 326.0289 2590.7849 0.000000000) (list 323.4657 2591.6317 0.000000000) (list 320.8639 2592.3517 0.000000000) (list 318.2300 2592.9432 0.000000000) (list 315.5702 2593.4047 0.000000000) (list 312.8909 2593.7352 0.000000000) (list 310.1987 2593.9338 0.000000000) (list 307.5000 2594.0000 0.000000000) (list 105.0000 2594.0000 0.000000000) (list 102.3013 2593.9338 0.000000000) (list 99.6091 2593.7352 0.000000000) (list 96.9298 2593.4047 0.000000000) (list 94.2700 2592.9432 0.000000000) (list 91.6361 2592.3517 0.000000000) (list 89.0343 2591.6317 0.000000000) (list 86.4711 2590.7849 0.000000000) (list 83.9524 2589.8134 0.000000000) (list 81.4845 2588.7194 0.000000000) (list 79.0732 2587.5057 0.000000000) (list 76.7243 2586.1751 0.000000000) (list 74.4436 2584.7308 0.000000000) (list 72.2365 2583.1764 0.000000000))))
  (setq s16p (append s16p (list (list 70.1084 2581.5156 0.000000000) (list 68.0643 2579.7523 0.000000000) (list 66.1091 2577.8909 0.000000000) (list 64.2477 2575.9357 0.000000000) (list 62.4844 2573.8916 0.000000000) (list 60.8236 2571.7635 0.000000000) (list 59.2692 2569.5564 0.000000000) (list 57.8249 2567.2757 0.000000000) (list 56.4943 2564.9268 0.000000000) (list 55.2806 2562.5155 0.000000000) (list 54.1866 2560.0476 0.000000000) (list 53.2151 2557.5289 0.000000000) (list 52.3683 2554.9657 0.000000000) (list 51.6483 2552.3639 0.000000000) (list 51.0568 2549.7300 0.000000000) (list 50.5953 2547.0702 0.000000000) (list 50.2648 2544.3909 0.000000000) (list 50.0662 2541.6987 0.000000000) (list 50.0000 2539.0000 0.000000000) (list 50.0000 144.0000 0.000000000) (list 50.0662 141.3013 0.000000000) (list 50.2648 138.6091 0.000000000) (list 50.5953 135.9298 0.000000000) (list 51.0568 133.2700 0.000000000) (list 51.6483 130.6361 0.000000000) (list 52.3683 128.0343 0.000000000) (list 53.2151 125.4711 0.000000000) (list 54.1866 122.9524 0.000000000) (list 55.2806 120.4845 0.000000000) (list 56.4943 118.0732 0.000000000) (list 57.8249 115.7243 0.000000000) (list 59.2692 113.4436 0.000000000) (list 60.8236 111.2365 0.000000000) (list 62.4844 109.1084 0.000000000) (list 64.2477 107.0643 0.000000000) (list 66.1091 105.1091 0.000000000) (list 68.0643 103.2477 0.000000000) (list 70.1084 101.4844 0.000000000) (list 72.2365 99.8236 0.000000000) (list 74.4436 98.2692 0.000000000))))
  (setq s16p (append s16p (list (list 76.7243 96.8249 0.000000000) (list 79.0732 95.4943 0.000000000) (list 81.4845 94.2806 0.000000000) (list 83.9524 93.1866 0.000000000) (list 86.4711 92.2151 0.000000000) (list 89.0343 91.3683 0.000000000) (list 91.6361 90.6483 0.000000000) (list 94.2700 90.0568 0.000000000) (list 96.9298 89.5953 0.000000000) (list 99.6091 89.2648 0.000000000) (list 102.3013 89.0662 0.000000000) (list 105.0000 89.0000 0.000000000))))
  (setq b (s16-extrude-y s16p 20 21 -381 171))
  (s16-sub a b)
  (s16-layer "$PART_S16_T-DOOR-L\U+02D90\U+02D90\U+00A8VVVV\U+02D90\U+00A8#0\U+00A816084" "64,54,46")
  (setq s16p nil)
  (setq s16p (append s16p (list (list 307.5000 83.0000 0.000000000) (list 310.4931 83.0735 0.000000000) (list 313.4790 83.2937 0.000000000) (list 316.4506 83.6602 0.000000000) (list 319.4005 84.1721 0.000000000) (list 322.3218 84.8281 0.000000000) (list 325.2074 85.6266 0.000000000) (list 328.0503 86.5658 0.000000000) (list 330.8437 87.6433 0.000000000) (list 333.5809 88.8567 0.000000000) (list 336.2552 90.2028 0.000000000) (list 338.8603 91.6786 0.000000000) (list 341.3898 93.2804 0.000000000) (list 343.8377 95.0043 0.000000000) (list 346.1980 96.8464 0.000000000) (list 348.4651 98.8020 0.000000000) (list 350.6335 100.8665 0.000000000) (list 352.6980 103.0349 0.000000000) (list 354.6536 105.3020 0.000000000) (list 356.4957 107.6623 0.000000000) (list 358.2196 110.1102 0.000000000) (list 359.8214 112.6397 0.000000000) (list 361.2972 115.2448 0.000000000) (list 362.6433 117.9191 0.000000000) (list 363.8567 120.6563 0.000000000) (list 364.9342 123.4497 0.000000000) (list 365.8734 126.2926 0.000000000) (list 366.6719 129.1782 0.000000000) (list 367.3279 132.0995 0.000000000) (list 367.8398 135.0494 0.000000000) (list 368.2063 138.0210 0.000000000) (list 368.4265 141.0069 0.000000000) (list 368.5000 144.0000 0.000000000) (list 368.5000 2539.0000 0.000000000) (list 368.4265 2541.9931 0.000000000) (list 368.2063 2544.9790 0.000000000) (list 367.8398 2547.9506 0.000000000) (list 367.3279 2550.9005 0.000000000) (list 366.6719 2553.8218 0.000000000) (list 365.8734 2556.7074 0.000000000))))
  (setq s16p (append s16p (list (list 364.9342 2559.5503 0.000000000) (list 363.8567 2562.3437 0.000000000) (list 362.6433 2565.0809 0.000000000) (list 361.2972 2567.7552 0.000000000) (list 359.8214 2570.3603 0.000000000) (list 358.2196 2572.8898 0.000000000) (list 356.4957 2575.3377 0.000000000) (list 354.6536 2577.6980 0.000000000) (list 352.6980 2579.9651 0.000000000) (list 350.6335 2582.1335 0.000000000) (list 348.4651 2584.1980 0.000000000) (list 346.1980 2586.1536 0.000000000) (list 343.8377 2587.9957 0.000000000) (list 341.3898 2589.7196 0.000000000) (list 338.8603 2591.3214 0.000000000) (list 336.2552 2592.7972 0.000000000) (list 333.5809 2594.1433 0.000000000) (list 330.8437 2595.3567 0.000000000) (list 328.0503 2596.4342 0.000000000) (list 325.2074 2597.3734 0.000000000) (list 322.3218 2598.1719 0.000000000) (list 319.4005 2598.8279 0.000000000) (list 316.4506 2599.3398 0.000000000) (list 313.4790 2599.7063 0.000000000) (list 310.4931 2599.9265 0.000000000) (list 307.5000 2600.0000 0.000000000) (list 105.0000 2600.0000 0.000000000) (list 102.0069 2599.9265 0.000000000) (list 99.0210 2599.7063 0.000000000) (list 96.0494 2599.3398 0.000000000) (list 93.0995 2598.8279 0.000000000) (list 90.1782 2598.1719 0.000000000) (list 87.2926 2597.3734 0.000000000) (list 84.4497 2596.4342 0.000000000) (list 81.6563 2595.3567 0.000000000) (list 78.9191 2594.1433 0.000000000) (list 76.2448 2592.7972 0.000000000) (list 73.6397 2591.3214 0.000000000) (list 71.1102 2589.7196 0.000000000) (list 68.6623 2587.9957 0.000000000))))
  (setq s16p (append s16p (list (list 66.3020 2586.1536 0.000000000) (list 64.0349 2584.1980 0.000000000) (list 61.8665 2582.1335 0.000000000) (list 59.8020 2579.9651 0.000000000) (list 57.8464 2577.6980 0.000000000) (list 56.0043 2575.3377 0.000000000) (list 54.2804 2572.8898 0.000000000) (list 52.6786 2570.3603 0.000000000) (list 51.2028 2567.7552 0.000000000) (list 49.8567 2565.0809 0.000000000) (list 48.6433 2562.3437 0.000000000) (list 47.5658 2559.5503 0.000000000) (list 46.6266 2556.7074 0.000000000) (list 45.8281 2553.8218 0.000000000) (list 45.1721 2550.9005 0.000000000) (list 44.6602 2547.9506 0.000000000) (list 44.2937 2544.9790 0.000000000) (list 44.0735 2541.9931 0.000000000) (list 44.0000 2539.0000 0.000000000) (list 44.0000 144.0000 0.000000000) (list 44.0735 141.0069 0.000000000) (list 44.2937 138.0210 0.000000000) (list 44.6602 135.0494 0.000000000) (list 45.1721 132.0995 0.000000000) (list 45.8281 129.1782 0.000000000) (list 46.6266 126.2926 0.000000000) (list 47.5658 123.4497 0.000000000) (list 48.6433 120.6563 0.000000000) (list 49.8567 117.9191 0.000000000) (list 51.2028 115.2448 0.000000000) (list 52.6786 112.6397 0.000000000) (list 54.2804 110.1102 0.000000000) (list 56.0043 107.6623 0.000000000) (list 57.8464 105.3020 0.000000000) (list 59.8020 103.0349 0.000000000) (list 61.8665 100.8665 0.000000000) (list 64.0349 98.8020 0.000000000) (list 66.3020 96.8464 0.000000000) (list 68.6623 95.0043 0.000000000) (list 71.1102 93.2804 0.000000000))))
  (setq s16p (append s16p (list (list 73.6397 91.6786 0.000000000) (list 76.2448 90.2028 0.000000000) (list 78.9191 88.8567 0.000000000) (list 81.6563 87.6433 0.000000000) (list 84.4497 86.5658 0.000000000) (list 87.2926 85.6266 0.000000000) (list 90.1782 84.8281 0.000000000) (list 93.0995 84.1721 0.000000000) (list 96.0494 83.6602 0.000000000) (list 99.0210 83.2937 0.000000000) (list 102.0069 83.0735 0.000000000) (list 105.0000 83.0000 0.000000000))))
  (setq b (s16-extrude-y s16p 11 21 -381 171))
  (s16-sub a b)
  (s16-layer "SZINES_Front" 81)
  (command "_.COPY" a "" '(0 0 0) '(5100 0 0)) (command "_.CHPROP" (entlast) "" "_LA" "SZINES_Front" "")
  ;; T-DOOR-R
  (s16-layer "$PART_S16_T-DOOR-R\U+02D90\U+02D90\U+00A8VVVV\U+02D90\U+00A8#0\U+00A816085" "64,54,46")
  (setq s16p nil)
  (setq s16p (append s16p (list (list 0.0000 0.0000 0.000000000) (list 412.5000 0.0000 0.000000000) (list 412.5000 2202.0000 0.414213562) (list 333.5000 2281.0000 0.000000000) (list 0.0000 2281.0000 0.000000000))))
  (setq a (s16-extrude-y s16p 18 436.5 -382 573))
  (s16-layer "SZINES_Front" 81)
  (command "_.COPY" a "" '(0 0 0) '(5100 0 0)) (command "_.CHPROP" (entlast) "" "_LA" "SZINES_Front" "")
  ;; TEXTILE
  (s16-layer "$PART_S16_TEXTILE\U+02D90\U+02D90\U+00A8KKKK\U+02D90\U+00A8#0\U+00A816086" "199,188,167")
  (setq s16p nil)
  (setq s16p (append s16p (list (list 262.5000 0.0000 0.414213562) (list 322.5000 60.0000 0.000000000) (list 322.5000 2455.0000 0.414213562) (list 262.5000 2515.0000 0.000000000) (list 60.0000 2515.0000 0.414213562) (list 0.0000 2455.0000 0.000000000) (list 0.0000 60.0000 0.414213562) (list 60.0000 0.0000 0.000000000))))
  (setq a (s16-extrude-y s16p 8 66.0 -366 255))
  (s16-layer "SZINES_Burkolat" 31)
  (command "_.COPY" a "" '(0 0 0) '(5100 0 0)) (command "_.CHPROP" (entlast) "" "_LA" "SZINES_Burkolat" "")
  ;; BG-1
  (s16-layer "$PART_S16_BG-1\U+02D90\U+02D90\U+00A80000\U+02D90\U+00A8#0\U+00A816087" "112,98,82")
  (setq a (s16-box 740 -25 470 811.0 17 2405))
  (s16-layer "SZINES_H\U+00E1tlemez" 17)
  (command "_.COPY" a "" '(0 0 0) '(5100 0 0)) (command "_.CHPROP" (entlast) "" "_LA" "SZINES_H\U+00E1tlemez" "")
  ;; BG-2
  (s16-layer "$PART_S16_BG-2\U+02D90\U+02D90\U+00A80000\U+02D90\U+00A8#0\U+00A816088" "112,98,82")
  (setq a (s16-box 1554.0 -25 470 679.5 17 2405))
  (s16-layer "SZINES_H\U+00E1tlemez" 17)
  (command "_.COPY" a "" '(0 0 0) '(5100 0 0)) (command "_.CHPROP" (entlast) "" "_LA" "SZINES_H\U+00E1tlemez" "")
  ;; BG-3
  (s16-layer "$PART_S16_BG-3\U+02D90\U+02D90\U+00A80000\U+02D90\U+00A8#0\U+00A816089" "112,98,82")
  (setq a (s16-box 2236.5 -25 470 679.5 17 2405))
  (s16-layer "SZINES_H\U+00E1tlemez" 17)
  (command "_.COPY" a "" '(0 0 0) '(5100 0 0)) (command "_.CHPROP" (entlast) "" "_LA" "SZINES_H\U+00E1tlemez" "")
  ;; BG-4
  (s16-layer "$PART_S16_BG-4\U+02D90\U+02D90\U+00A80000\U+02D90\U+00A8#0\U+00A816090" "112,98,82")
  (setq a (s16-box 2919 -25 470 678.0 17 2405))
  (s16-layer "SZINES_H\U+00E1tlemez" 17)
  (command "_.COPY" a "" '(0 0 0) '(5100 0 0)) (command "_.CHPROP" (entlast) "" "_LA" "SZINES_H\U+00E1tlemez" "")
  ;; BATTEN-1
  (s16-layer "$PART_S16_BATTEN-1\U+02D90\U+02D90\U+00A80000\U+02D90\U+00A8#0\U+00A816091" "138,127,114")
  (setq a (s16-box 910 -8 590 40 8 2235))
  (s16-layer "SZINES_H\U+00E1tlemez" 17)
  (command "_.COPY" a "" '(0 0 0) '(5100 0 0)) (command "_.CHPROP" (entlast) "" "_LA" "SZINES_H\U+00E1tlemez" "")
  ;; BATTEN-2
  (s16-layer "$PART_S16_BATTEN-2\U+02D90\U+02D90\U+00A80000\U+02D90\U+00A8#0\U+00A816092" "138,127,114")
  (setq a (s16-box 1540 -8 590 40 8 2235))
  (s16-layer "SZINES_H\U+00E1tlemez" 17)
  (command "_.COPY" a "" '(0 0 0) '(5100 0 0)) (command "_.CHPROP" (entlast) "" "_LA" "SZINES_H\U+00E1tlemez" "")
  ;; BATTEN-3
  (s16-layer "$PART_S16_BATTEN-3\U+02D90\U+02D90\U+00A80000\U+02D90\U+00A8#0\U+00A816093" "138,127,114")
  (setq a (s16-box 2220 -8 590 40 8 2235))
  (s16-layer "SZINES_H\U+00E1tlemez" 17)
  (command "_.COPY" a "" '(0 0 0) '(5100 0 0)) (command "_.CHPROP" (entlast) "" "_LA" "SZINES_H\U+00E1tlemez" "")
  ;; BATTEN-4
  (s16-layer "$PART_S16_BATTEN-4\U+02D90\U+02D90\U+00A80000\U+02D90\U+00A8#0\U+00A816094" "138,127,114")
  (setq a (s16-box 2900 -8 590 40 8 2235))
  (s16-layer "SZINES_H\U+00E1tlemez" 17)
  (command "_.COPY" a "" '(0 0 0) '(5100 0 0)) (command "_.CHPROP" (entlast) "" "_LA" "SZINES_H\U+00E1tlemez" "")
  ;; BATTEN-5
  (s16-layer "$PART_S16_BATTEN-5\U+02D90\U+02D90\U+00A80000\U+02D90\U+00A8#0\U+00A816095" "138,127,114")
  (setq a (s16-box 3530 -8 590 40 8 2235))
  (s16-layer "SZINES_H\U+00E1tlemez" 17)
  (command "_.COPY" a "" '(0 0 0) '(5100 0 0)) (command "_.CHPROP" (entlast) "" "_LA" "SZINES_H\U+00E1tlemez" "")
  ;; CURVE-T-TOP
  (s16-layer "$PART_S16_CURVE-T-TOP\U+02D90\U+02D90\U+00A8FFFF\U+02D90\U+00A8#0\U+00A816096" "51,44,38")
  (setq s16p nil)
  (setq s16p (append s16p (list (list 0.0000 0.0000 -0.414213562) (list 100.0000 100.0000 0.000000000) (list 770.0000 100.0000 -0.414213562) (list 870.0000 0.0000 0.000000000) (list 852.0000 0.0000 0.414213562) (list 770.0000 82.0000 0.000000000) (list 100.0000 82.0000 0.414213562) (list 18.0000 0.0000 0.000000000))))
  (setq a (s16-extrude-y s16p 337 0 -40 2775))
  (s16-layer "SZINES_Tet\U+0151" 173)
  (command "_.COPY" a "" '(0 0 0) '(5100 0 0)) (command "_.CHPROP" (entlast) "" "_LA" "SZINES_Tet\U+0151" "")
  ;; FRAME-T-TOP
  (s16-layer "$PART_S16_FRAME-T-TOP\U+02D90\U+02D90\U+00A8FFFF\U+02D90\U+00A8#0\U+00A816097" "51,44,38")
  (setq s16p nil)
  (setq s16p (append s16p (list (list 0.0000 0.0000 -0.414213562) (list 100.0000 100.0000 0.000000000) (list 770.0000 100.0000 -0.414213562) (list 870.0000 0.0000 0.000000000) (list 852.0000 0.0000 0.414213562) (list 770.0000 82.0000 0.000000000) (list 100.0000 82.0000 0.414213562) (list 18.0000 0.0000 0.000000000))))
  (setq a (s16-extrude-y s16p 18 0 -382 2775))
  (s16-layer "SZINES_Front" 81)
  (command "_.COPY" a "" '(0 0 0) '(5100 0 0)) (command "_.CHPROP" (entlast) "" "_LA" "SZINES_Front" "")
  ;; CURVE-T-BOT
  (s16-layer "$PART_S16_CURVE-T-BOT\U+02D90\U+02D90\U+00A8FFF0\U+02D90\U+00A8#0\U+00A816098" "51,44,38")
  (setq s16p nil)
  (setq s16p (append s16p (list (list 0.0000 100.0000 0.414213562) (list 100.0000 0.0000 0.000000000) (list 870.0000 0.0000 0.000000000) (list 870.0000 18.0000 0.000000000) (list 100.0000 18.0000 -0.414213562) (list 18.0000 100.0000 0.000000000))))
  (setq a (s16-extrude-y s16p 337 0 -40 150))
  (s16-layer "SZINES_Tet\U+0151" 173)
  (command "_.COPY" a "" '(0 0 0) '(5100 0 0)) (command "_.CHPROP" (entlast) "" "_LA" "SZINES_Tet\U+0151" "")
  ;; FRAME-T-BOT
  (s16-layer "$PART_S16_FRAME-T-BOT\U+02D90\U+02D90\U+00A8FFFF\U+02D90\U+00A8#0\U+00A816099" "51,44,38")
  (setq s16p nil)
  (setq s16p (append s16p (list (list 0.0000 100.0000 0.414213562) (list 100.0000 0.0000 0.000000000) (list 870.0000 0.0000 0.000000000) (list 870.0000 18.0000 0.000000000) (list 100.0000 18.0000 -0.414213562) (list 18.0000 100.0000 0.000000000))))
  (setq a (s16-extrude-y s16p 18 0 -382 150))
  (s16-layer "SZINES_Front" 81)
  (command "_.COPY" a "" '(0 0 0) '(5100 0 0)) (command "_.CHPROP" (entlast) "" "_LA" "SZINES_Front" "")
  ;; FRAME-T-L
  (s16-layer "$PART_S16_FRAME-T-L\U+02D90\U+02D90\U+00A8FF00\U+02D90\U+00A8#0\U+00A816100" "51,44,38")
  (setq a (s16-box 0 -400 250 18 18 2525))
  (s16-layer "SZINES_Keret" 33)
  (command "_.COPY" a "" '(0 0 0) '(5100 0 0)) (command "_.CHPROP" (entlast) "" "_LA" "SZINES_Keret" "")
  ;; FRAME-T-R
  (s16-layer "$PART_S16_FRAME-T-R\U+02D90\U+02D90\U+00A8FF00\U+02D90\U+00A8#0\U+00A816101" "51,44,38")
  (setq a (s16-box 852 -400 570 18 18 2205))
  (s16-layer "SZINES_Keret" 33)
  (command "_.COPY" a "" '(0 0 0) '(5100 0 0)) (command "_.CHPROP" (entlast) "" "_LA" "SZINES_Keret" "")
  ;; FRAME-T-MID
  (s16-layer "$PART_S16_FRAME-T-MID\U+02D90\U+02D90\U+00A8FFF0\U+02D90\U+00A8#0\U+00A816102" "51,44,38")
  (setq a (s16-box 436.5 -400 552 433.5 18 18))
  (s16-layer "SZINES_Voszt\U+00F3" 93)
  (command "_.COPY" a "" '(0 0 0) '(5100 0 0)) (command "_.CHPROP" (entlast) "" "_LA" "SZINES_Voszt\U+00F3" "")
  ;; FRAME-B-LOW-1
  (s16-layer "$PART_S16_FRAME-B-LOW-1\U+02D90\U+02D90\U+00A8FF00\U+02D90\U+00A8#0\U+00A816103" "51,44,38")
  (setq a (s16-box 870 -400 150 850 18 18))
  (s16-layer "SZINES_Keret" 33)
  (command "_.COPY" a "" '(0 0 0) '(5100 0 0)) (command "_.CHPROP" (entlast) "" "_LA" "SZINES_Keret" "")
  ;; FRAME-B-LOW-2
  (s16-layer "$PART_S16_FRAME-B-LOW-2\U+02D90\U+02D90\U+00A8FF00\U+02D90\U+00A8#0\U+00A816104" "51,44,38")
  (setq a (s16-box 1720 -400 150 1030 18 18))
  (s16-layer "SZINES_Keret" 33)
  (command "_.COPY" a "" '(0 0 0) '(5100 0 0)) (command "_.CHPROP" (entlast) "" "_LA" "SZINES_Keret" "")
  ;; FRAME-B-LOW-3
  (s16-layer "$PART_S16_FRAME-B-LOW-3\U+02D90\U+02D90\U+00A8FF00\U+02D90\U+00A8#0\U+00A816105" "51,44,38")
  (setq a (s16-box 2750 -400 150 770 18 18))
  (s16-layer "SZINES_Keret" 33)
  (command "_.COPY" a "" '(0 0 0) '(5100 0 0)) (command "_.CHPROP" (entlast) "" "_LA" "SZINES_Keret" "")
  ;; FRAME-B-HIGH-1
  (s16-layer "$PART_S16_FRAME-B-HIGH-1\U+02D90\U+02D90\U+00A8FF00\U+02D90\U+00A8#0\U+00A816106" "51,44,38")
  (setq a (s16-box 870 -400 552 850 18 18))
  (s16-layer "SZINES_Keret" 33)
  (command "_.COPY" a "" '(0 0 0) '(5100 0 0)) (command "_.CHPROP" (entlast) "" "_LA" "SZINES_Keret" "")
  ;; FRAME-B-HIGH-2
  (s16-layer "$PART_S16_FRAME-B-HIGH-2\U+02D90\U+02D90\U+00A8FF00\U+02D90\U+00A8#0\U+00A816107" "51,44,38")
  (setq a (s16-box 1720 -400 552 1030 18 18))
  (s16-layer "SZINES_Keret" 33)
  (command "_.COPY" a "" '(0 0 0) '(5100 0 0)) (command "_.CHPROP" (entlast) "" "_LA" "SZINES_Keret" "")
  ;; FRAME-B-HIGH-3
  (s16-layer "$PART_S16_FRAME-B-HIGH-3\U+02D90\U+02D90\U+00A8FF00\U+02D90\U+00A8#0\U+00A816108" "51,44,38")
  (setq a (s16-box 2750 -400 552 770 18 18))
  (s16-layer "SZINES_Keret" 33)
  (command "_.COPY" a "" '(0 0 0) '(5100 0 0)) (command "_.CHPROP" (entlast) "" "_LA" "SZINES_Keret" "")
  ;; FRAME-B-TOP
  (s16-layer "$PART_S16_FRAME-B-TOP\U+02D90\U+02D90\U+00A8FFFF\U+02D90\U+00A8#0\U+00A816109" "51,44,38")
  (setq s16p nil)
  (setq s16p (append s16p (list (list 0.0000 80.0000 -0.414213562) (list 80.0000 0.0000 0.000000000) (list 62.0000 0.0000 0.414213562) (list 0.0000 62.0000 0.000000000))))
  (setq a (s16-extrude-y s16p 18 3520 -382 490))
  (s16-layer "SZINES_Keret" 33)
  (command "_.COPY" a "" '(0 0 0) '(5100 0 0)) (command "_.CHPROP" (entlast) "" "_LA" "SZINES_Keret" "")
  ;; CURVE-B-TOP
  (s16-layer "$PART_S16_CURVE-B-TOP\U+02D90\U+02D90\U+00A8FFFF\U+02D90\U+00A8#0\U+00A816110" "51,44,38")
  (setq s16p nil)
  (setq s16p (append s16p (list (list 0.0000 80.0000 -0.414213562) (list 80.0000 0.0000 0.000000000) (list 62.0000 0.0000 0.414213562) (list 0.0000 62.0000 0.000000000))))
  (setq a (s16-extrude-y s16p 337 3520 -40 490))
  (s16-layer "SZINES_Keret" 33)
  (command "_.COPY" a "" '(0 0 0) '(5100 0 0)) (command "_.CHPROP" (entlast) "" "_LA" "SZINES_Keret" "")
  ;; FRAME-B-BOT
  (s16-layer "$PART_S16_FRAME-B-BOT\U+02D90\U+02D90\U+00A8FFFF\U+02D90\U+00A8#0\U+00A816111" "51,44,38")
  (setq s16p nil)
  (setq s16p (append s16p (list (list 0.0000 18.0000 0.414213562) (list 62.0000 80.0000 0.000000000) (list 80.0000 80.0000 -0.414213562) (list 0.0000 0.0000 0.000000000))))
  (setq a (s16-extrude-y s16p 18 3520 -382 150))
  (s16-layer "SZINES_Keret" 33)
  (command "_.COPY" a "" '(0 0 0) '(5100 0 0)) (command "_.CHPROP" (entlast) "" "_LA" "SZINES_Keret" "")
  ;; CURVE-B-BOT
  (s16-layer "$PART_S16_CURVE-B-BOT\U+02D90\U+02D90\U+00A8FFFF\U+02D90\U+00A8#0\U+00A816112" "51,44,38")
  (setq s16p nil)
  (setq s16p (append s16p (list (list 0.0000 18.0000 0.414213562) (list 62.0000 80.0000 0.000000000) (list 80.0000 80.0000 -0.414213562) (list 0.0000 0.0000 0.000000000))))
  (setq a (s16-extrude-y s16p 337 3520 -40 150))
  (s16-layer "SZINES_Keret" 33)
  (command "_.COPY" a "" '(0 0 0) '(5100 0 0)) (command "_.CHPROP" (entlast) "" "_LA" "SZINES_Keret" "")
  ;; FRAME-B-R
  (s16-layer "$PART_S16_FRAME-B-R\U+02D90\U+02D90\U+00A8FF00\U+02D90\U+00A8#0\U+00A816113" "51,44,38")
  (setq a (s16-box 3582 -400 230 18 18 260))
  (s16-layer "SZINES_Keret" 33)
  (command "_.COPY" a "" '(0 0 0) '(5100 0 0)) (command "_.CHPROP" (entlast) "" "_LA" "SZINES_Keret" "")
  ;; TV-SPACER-1
  (s16-layer "$PART_S16_TV-SPACER-1\U+02D90\U+02D90\U+00A8FFFF\U+02D90\U+00A8#0\U+00A816114" "51,44,38")
  (setq a (s16-box 910 -95 605 2530 69 30))
  (s16-layer "SZINES_K\U+00F6t\U+0151" 153)
  (command "_.COPY" a "" '(0 0 0) '(5100 0 0)) (command "_.CHPROP" (entlast) "" "_LA" "SZINES_K\U+00F6t\U+0151" "")
  ;; TV-SPACER-2
  (s16-layer "$PART_S16_TV-SPACER-2\U+02D90\U+02D90\U+00A8FFFF\U+02D90\U+00A8#0\U+00A816115" "51,44,38")
  (setq a (s16-box 1340 -95 2050 2020 69 30))
  (s16-layer "SZINES_K\U+00F6t\U+0151" 153)
  (command "_.COPY" a "" '(0 0 0) '(5100 0 0)) (command "_.CHPROP" (entlast) "" "_LA" "SZINES_K\U+00F6t\U+0151" "")
  ;; T-LOW-DIV
  (s16-layer "$PART_S16_T-LOW-DIV\U+02D90\U+02D90\U+00A8V000\U+02D90\U+00A8#0\U+00A816116" "80,73,66")
  (setq a (s16-box 417 -377 168 18 337 402))
  (s16-layer "SZINES_Oldal" 40)
  (command "_.COPY" a "" '(0 0 0) '(5100 0 0)) (command "_.CHPROP" (entlast) "" "_LA" "SZINES_Oldal" "")
  ;; T-LOW-BACK
  (s16-layer "$PART_S16_T-LOW-BACK\U+02D90\U+02D90\U+00A80000\U+02D90\U+00A8#0\U+00A816117" "105,108,103")
  (setq s16p nil)
  (setq s16p (append s16p (list (list 0.0000 402.0000 0.000000000) (list 399.0000 402.0000 0.000000000) (list 399.0000 0.0000 0.000000000) (list 82.0000 0.0000 -0.414213562) (list 0.0000 82.0000 0.000000000))))
  (setq a (s16-extrude-y s16p 8 18 -40 168))
  (s16-layer "SZINES_H\U+00E1tlemez" 17)
  (command "_.COPY" a "" '(0 0 0) '(5100 0 0)) (command "_.CHPROP" (entlast) "" "_LA" "SZINES_H\U+00E1tlemez" "")
  ;; T-DOOR-L-BACK
  (s16-layer "$PART_S16_T-DOOR-L-BACK\U+02D90\U+02D90\U+00A8FFFF\U+02D90\U+00A8#0\U+00A816118" "51,44,38")
  (setq s16p nil)
  (setq s16p (append s16p (list (list 267.5000 0.0000 0.000000000) (list 270.6894 0.0783 0.000000000) (list 273.8711 0.3130 0.000000000) (list 277.0375 0.7035 0.000000000) (list 280.1809 1.2490 0.000000000) (list 283.2937 1.9480 0.000000000) (list 286.3685 2.7989 0.000000000) (list 289.3978 3.7996 0.000000000) (list 292.3744 4.9478 0.000000000) (list 295.2911 6.2407 0.000000000) (list 298.1408 7.6751 0.000000000) (list 300.9167 9.2476 0.000000000) (list 303.6121 10.9545 0.000000000) (list 306.2205 12.7915 0.000000000) (list 308.7356 14.7543 0.000000000) (list 311.1513 16.8382 0.000000000) (list 313.4619 19.0381 0.000000000) (list 315.6618 21.3487 0.000000000) (list 317.7457 23.7644 0.000000000) (list 319.7085 26.2795 0.000000000) (list 321.5455 28.8879 0.000000000) (list 323.2524 31.5833 0.000000000) (list 324.8249 34.3592 0.000000000) (list 326.2593 37.2089 0.000000000) (list 327.5522 40.1256 0.000000000) (list 328.7004 43.1022 0.000000000) (list 329.7011 46.1315 0.000000000) (list 330.5520 49.2063 0.000000000) (list 331.2510 52.3191 0.000000000) (list 331.7965 55.4625 0.000000000) (list 332.1870 58.6289 0.000000000) (list 332.4217 61.8106 0.000000000) (list 332.5000 65.0000 0.000000000) (list 332.5000 2460.0000 0.000000000) (list 332.4217 2463.1894 0.000000000) (list 332.1870 2466.3711 0.000000000) (list 331.7965 2469.5375 0.000000000) (list 331.2510 2472.6809 0.000000000) (list 330.5520 2475.7937 0.000000000) (list 329.7011 2478.8685 0.000000000))))
  (setq s16p (append s16p (list (list 328.7004 2481.8978 0.000000000) (list 327.5522 2484.8744 0.000000000) (list 326.2593 2487.7911 0.000000000) (list 324.8249 2490.6408 0.000000000) (list 323.2524 2493.4167 0.000000000) (list 321.5455 2496.1121 0.000000000) (list 319.7085 2498.7205 0.000000000) (list 317.7457 2501.2356 0.000000000) (list 315.6618 2503.6513 0.000000000) (list 313.4619 2505.9619 0.000000000) (list 311.1513 2508.1618 0.000000000) (list 308.7356 2510.2457 0.000000000) (list 306.2205 2512.2085 0.000000000) (list 303.6121 2514.0455 0.000000000) (list 300.9167 2515.7524 0.000000000) (list 298.1408 2517.3249 0.000000000) (list 295.2911 2518.7593 0.000000000) (list 292.3744 2520.0522 0.000000000) (list 289.3978 2521.2004 0.000000000) (list 286.3685 2522.2011 0.000000000) (list 283.2937 2523.0520 0.000000000) (list 280.1809 2523.7510 0.000000000) (list 277.0375 2524.2965 0.000000000) (list 273.8711 2524.6870 0.000000000) (list 270.6894 2524.9217 0.000000000) (list 267.5000 2525.0000 0.000000000) (list 65.0000 2525.0000 0.000000000) (list 61.8106 2524.9217 0.000000000) (list 58.6289 2524.6870 0.000000000) (list 55.4625 2524.2965 0.000000000) (list 52.3191 2523.7510 0.000000000) (list 49.2063 2523.0520 0.000000000) (list 46.1315 2522.2011 0.000000000) (list 43.1022 2521.2004 0.000000000) (list 40.1256 2520.0522 0.000000000) (list 37.2089 2518.7593 0.000000000) (list 34.3592 2517.3249 0.000000000) (list 31.5833 2515.7524 0.000000000) (list 28.8879 2514.0455 0.000000000) (list 26.2795 2512.2085 0.000000000))))
  (setq s16p (append s16p (list (list 23.7644 2510.2457 0.000000000) (list 21.3487 2508.1618 0.000000000) (list 19.0381 2505.9619 0.000000000) (list 16.8382 2503.6513 0.000000000) (list 14.7543 2501.2356 0.000000000) (list 12.7915 2498.7205 0.000000000) (list 10.9545 2496.1121 0.000000000) (list 9.2476 2493.4167 0.000000000) (list 7.6751 2490.6408 0.000000000) (list 6.2407 2487.7911 0.000000000) (list 4.9478 2484.8744 0.000000000) (list 3.7996 2481.8978 0.000000000) (list 2.7989 2478.8685 0.000000000) (list 1.9480 2475.7937 0.000000000) (list 1.2490 2472.6809 0.000000000) (list 0.7035 2469.5375 0.000000000) (list 0.3130 2466.3711 0.000000000) (list 0.0783 2463.1894 0.000000000) (list 0.0000 2460.0000 0.000000000) (list 0.0000 65.0000 0.000000000) (list 0.0783 61.8106 0.000000000) (list 0.3130 58.6289 0.000000000) (list 0.7035 55.4625 0.000000000) (list 1.2490 52.3191 0.000000000) (list 1.9480 49.2063 0.000000000) (list 2.7989 46.1315 0.000000000) (list 3.7996 43.1022 0.000000000) (list 4.9478 40.1256 0.000000000) (list 6.2407 37.2089 0.000000000) (list 7.6751 34.3592 0.000000000) (list 9.2476 31.5833 0.000000000) (list 10.9545 28.8879 0.000000000) (list 12.7915 26.2795 0.000000000) (list 14.7543 23.7644 0.000000000) (list 16.8382 21.3487 0.000000000) (list 19.0381 19.0381 0.000000000) (list 21.3487 16.8382 0.000000000) (list 23.7644 14.7543 0.000000000) (list 26.2795 12.7915 0.000000000) (list 28.8879 10.9545 0.000000000))))
  (setq s16p (append s16p (list (list 31.5833 9.2476 0.000000000) (list 34.3592 7.6751 0.000000000) (list 37.2089 6.2407 0.000000000) (list 40.1256 4.9478 0.000000000) (list 43.1022 3.7996 0.000000000) (list 46.1315 2.7989 0.000000000) (list 49.2063 1.9480 0.000000000) (list 52.3191 1.2490 0.000000000) (list 55.4625 0.7035 0.000000000) (list 58.6289 0.3130 0.000000000) (list 61.8106 0.0783 0.000000000) (list 65.0000 0.0000 0.000000000))))
  (setq a (s16-extrude-y s16p 12 61.0 -354 250))
  (s16-layer "SZINES_Front" 81)
  (command "_.COPY" a "" '(0 0 0) '(5100 0 0)) (command "_.CHPROP" (entlast) "" "_LA" "SZINES_Front" "")
  ;; TV-FIELD
  (s16-layer "$DIFF_OUT" 1)
  (setq b (s16-box 869 -114 569 2629 13 27))
  (s16-layer "$PART_S16_TV-FIELD\U+02D90\U+02D90\U+00A8VVVV\U+02D90\U+00A8#0\U+00A816119" "64,54,46")
  (setq s16p nil)
  (setq s16p (append s16p (list (list 0.0000 0.0000 0.000000000) (list 2630.0000 0.0000 0.000000000) (list 2630.0000 100.0000 0.000000000) (list 2630.0000 1480.0000 0.000000000) (list 2629.8795 1484.9068 0.000000000) (list 2629.5185 1489.8017 0.000000000) (list 2628.9177 1494.6730 0.000000000) (list 2628.0785 1499.5090 0.000000000) (list 2627.0031 1504.2980 0.000000000) (list 2625.6940 1509.0285 0.000000000) (list 2624.1544 1513.6890 0.000000000) (list 2622.3880 1518.2683 0.000000000) (list 2620.3989 1522.7555 0.000000000) (list 2618.1921 1527.1397 0.000000000) (list 2615.7729 1531.4103 0.000000000) (list 2613.1470 1535.5570 0.000000000) (list 2610.3208 1539.5699 0.000000000) (list 2607.3010 1543.4393 0.000000000) (list 2604.0951 1547.1559 0.000000000) (list 2600.7107 1550.7107 0.000000000) (list 2597.1559 1554.0951 0.000000000) (list 2593.4393 1557.3010 0.000000000) (list 2589.5699 1560.3208 0.000000000) (list 2585.5570 1563.1470 0.000000000) (list 2581.4103 1565.7729 0.000000000) (list 2577.1397 1568.1921 0.000000000) (list 2572.7555 1570.3989 0.000000000) (list 2568.2683 1572.3880 0.000000000) (list 2563.6890 1574.1544 0.000000000) (list 2559.0285 1575.6940 0.000000000) (list 2554.2980 1577.0031 0.000000000) (list 2549.5090 1578.0785 0.000000000) (list 2544.6730 1578.9177 0.000000000) (list 2539.8017 1579.5185 0.000000000) (list 2534.9068 1579.8795 0.000000000) (list 2530.0000 1580.0000 0.000000000) (list 450.0000 1580.0000 0.000000000) (list 443.1305 1579.8314 0.000000000) (list 436.2776 1579.3259 0.000000000) (list 429.4577 1578.4847 0.000000000))))
  (setq s16p (append s16p (list (list 422.6874 1577.3099 0.000000000) (list 415.9828 1575.8044 0.000000000) (list 409.3601 1573.9716 0.000000000) (list 402.8354 1571.8162 0.000000000) (list 396.4243 1569.3431 0.000000000) (list 390.1423 1566.5585 0.000000000) (list 384.0045 1563.4690 0.000000000) (list 378.0256 1560.0820 0.000000000) (list 372.2202 1556.4057 0.000000000) (list 366.6021 1552.4491 0.000000000) (list 361.1849 1548.2215 0.000000000) (list 355.9817 1543.7332 0.000000000) (list 351.0051 1538.9949 0.000000000) (list 346.2668 1534.0183 0.000000000) (list 341.7785 1528.8151 0.000000000) (list 337.5509 1523.3979 0.000000000) (list 333.5943 1517.7798 0.000000000) (list 329.9180 1511.9744 0.000000000) (list 326.5310 1505.9955 0.000000000) (list 323.4415 1499.8577 0.000000000) (list 320.6569 1493.5757 0.000000000) (list 318.1838 1487.1646 0.000000000) (list 316.0284 1480.6399 0.000000000) (list 314.1956 1474.0172 0.000000000) (list 312.6901 1467.3126 0.000000000) (list 311.5153 1460.5423 0.000000000) (list 310.6741 1453.7224 0.000000000) (list 310.1686 1446.8695 0.000000000) (list 310.0000 1440.0000 0.000000000) (list 310.0000 540.0000 0.000000000) (list 309.8073 532.1492 0.000000000) (list 309.2296 524.3173 0.000000000) (list 308.2682 516.5231 0.000000000) (list 306.9256 508.7855 0.000000000) (list 305.2050 501.1232 0.000000000) (list 303.1105 493.5545 0.000000000) (list 300.6471 486.0976 0.000000000) (list 297.8207 478.7707 0.000000000) (list 294.6383 471.5912 0.000000000) (list 291.1074 464.5765 0.000000000))))
  (setq s16p (append s16p (list (list 287.2366 457.7436 0.000000000) (list 283.0351 451.1088 0.000000000) (list 278.5132 444.6881 0.000000000) (list 273.6817 438.4971 0.000000000) (list 268.5522 432.5506 0.000000000) (list 263.1371 426.8629 0.000000000) (list 257.4494 421.4478 0.000000000) (list 251.5029 416.3183 0.000000000) (list 245.3119 411.4868 0.000000000) (list 238.8912 406.9649 0.000000000) (list 232.2564 402.7634 0.000000000) (list 225.4235 398.8926 0.000000000) (list 218.4088 395.3617 0.000000000) (list 211.2293 392.1793 0.000000000) (list 203.9024 389.3529 0.000000000) (list 196.4455 386.8895 0.000000000) (list 188.8768 384.7950 0.000000000) (list 181.2145 383.0744 0.000000000) (list 173.4769 381.7318 0.000000000) (list 165.6827 380.7704 0.000000000) (list 157.8508 380.1927 0.000000000) (list 150.0000 380.0000 0.000000000) (list 0.0000 380.0000 0.000000000))))
  (setq a (s16-extrude-y s16p 18 870 -95 570))
  (s16-layer "$PART_S16_TV-FIELD\U+02D90\U+02D90\U+00A8VVVV\U+02D90\U+00A8#0\U+00A816119" "64,54,46")
  (setq b (s16-box 869 -114 569 2629 13 27))
  (s16-sub a b)
  (s16-layer "SZINES_Burkolat" 31)
  (command "_.COPY" a "" '(0 0 0) '(5100 0 0)) (command "_.CHPROP" (entlast) "" "_LA" "SZINES_Burkolat" "")
  ;; BG-FINISH
  (s16-layer "$PART_S16_BG-FINISH\U+02D90\U+02D90\U+00A80000\U+02D90\U+00A8#0\U+00A816120" "112,98,82")
  (setq a (s16-box 740 -26 470 2857 1 2405))
  (s16-layer "SZINES_H\U+00E1tlemez" 17)
  (command "_.COPY" a "" '(0 0 0) '(5100 0 0)) (command "_.CHPROP" (entlast) "" "_LA" "SZINES_H\U+00E1tlemez" "")
  ;; TOP-WASH-COVER
  (s16-layer "$PART_S16_TOP-WASH-COVER\U+02D90\U+02D90\U+00A80000\U+02D90\U+00A8#0\U+00A816121" "42,38,34")
  (setq a (s16-box 740.0 -34.0 2872.0 2857.0 8.0 3.0))
  (s16-layer "SZINES_F\U+00E9ny" 121)
  (command "_.COPY" a "" '(0 0 0) '(5100 0 0)) (command "_.CHPROP" (entlast) "" "_LA" "SZINES_F\U+00E9ny" "")
  ;; TOP-WASH-BAFFLE
  (s16-layer "$PART_S16_TOP-WASH-BAFFLE\U+02D90\U+02D90\U+00A80000\U+02D90\U+00A8#0\U+00A816122" "42,38,34")
  (setq a (s16-box 740.0 -38.0 2857.0 2857.0 4.0 18.0))
  (s16-layer "SZINES_F\U+00E9ny" 121)
  (command "_.COPY" a "" '(0 0 0) '(5100 0 0)) (command "_.CHPROP" (entlast) "" "_LA" "SZINES_F\U+00E9ny" "")
  ;; TOP-WASH-HIDDEN-END
  (s16-layer "$PART_S16_TOP-WASH-HIDDEN-END\U+02D90\U+02D90\U+00A80000\U+02D90\U+00A8#0\U+00A816123" "42,38,34")
  (setq a (s16-box 3595.0 -34.0 2857.0 2.0 8.0 15.0))
  (s16-layer "SZINES_F\U+00E9ny" 121)
  (command "_.COPY" a "" '(0 0 0) '(5100 0 0)) (command "_.CHPROP" (entlast) "" "_LA" "SZINES_F\U+00E9ny" "")
  ;; UPLIGHT-TRAY
  (s16-layer "$PART_S16_UPLIGHT-TRAY\U+02D90\U+02D90\U+00A80000\U+02D90\U+00A8#0\U+00A816124" "42,38,34")
  (setq a (s16-box 740.0 -29.0 2875.0 2845.0 24.0 1.0))
  (s16-layer "SZINES_F\U+00E9ny" 121)
  (command "_.COPY" a "" '(0 0 0) '(5100 0 0)) (command "_.CHPROP" (entlast) "" "_LA" "SZINES_F\U+00E9ny" "")
  ;; UPLIGHT-FRONT-VISOR
  (s16-layer "$PART_S16_UPLIGHT-FRONT-VISOR\U+02D90\U+02D90\U+00A80000\U+02D90\U+00A8#0\U+00A816125" "42,38,34")
  (setq a (s16-box 740.0 -29.0 2876.0 2845.0 4.0 3.0))
  (s16-layer "SZINES_Front" 81)
  (command "_.COPY" a "" '(0 0 0) '(5100 0 0)) (command "_.CHPROP" (entlast) "" "_LA" "SZINES_Front" "")
  ;; UPLIGHT-REAR-VISOR
  (s16-layer "$PART_S16_UPLIGHT-REAR-VISOR\U+02D90\U+02D90\U+00A80000\U+02D90\U+00A8#0\U+00A816126" "42,38,34")
  (setq a (s16-box 740.0 -8.0 2876.0 2845.0 3.0 3.0))
  (s16-layer "SZINES_F\U+00E9ny" 121)
  (command "_.COPY" a "" '(0 0 0) '(5100 0 0)) (command "_.CHPROP" (entlast) "" "_LA" "SZINES_F\U+00E9ny" "")
  ;; DECK-CONTINUOUS-COVER
  (s16-layer "$PART_S16_DECK-CONTINUOUS-COVER\U+02D90\U+02D90\U+00A80000\U+02D90\U+00A8#0\U+00A816127" "42,38,34")
  (setq a (s16-box 870.0 -109.0 592.0 2628.0 8.0 4.0))
  (s16-layer "SZINES_F\U+00E9ny" 121)
  (command "_.COPY" a "" '(0 0 0) '(5100 0 0)) (command "_.CHPROP" (entlast) "" "_LA" "SZINES_F\U+00E9ny" "")
  ;; DECK-CONTINUOUS-BAFFLE
  (s16-layer "$PART_S16_DECK-CONTINUOUS-BAFFLE\U+02D90\U+02D90\U+00A80000\U+02D90\U+00A8#0\U+00A816128" "42,38,34")
  (setq a (s16-box 870.0 -113.0 579.0 2628.0 4.0 17.0))
  (s16-layer "SZINES_F\U+00E9ny" 121)
  (command "_.COPY" a "" '(0 0 0) '(5100 0 0)) (command "_.CHPROP" (entlast) "" "_LA" "SZINES_F\U+00E9ny" "")
  ;; LOW-INTERNAL-LIGHT-VISOR
  (s16-layer "$PART_S16_LOW-INTERNAL-LIGHT-VISOR\U+02D90\U+02D90\U+00A80000\U+02D90\U+00A8#0\U+00A816129" "42,38,34")
  (setq a (s16-box 57.0 -348.0 554.0 306.0 5.0 16.0))
  (s16-layer "SZINES_F\U+00E9ny" 121)
  (command "_.COPY" a "" '(0 0 0) '(5100 0 0)) (command "_.CHPROP" (entlast) "" "_LA" "SZINES_F\U+00E9ny" "")
  (command "_.ZOOM" "_E")
  (princ "\nS16-R15C-GY-v1: 129 alkatrész felépítve.")
  (princ))
(princ "\nS16 betöltve: (s16-build) majd (s16-readback \"/Users/<te>/CAD/s16_readback\")")
(princ)
