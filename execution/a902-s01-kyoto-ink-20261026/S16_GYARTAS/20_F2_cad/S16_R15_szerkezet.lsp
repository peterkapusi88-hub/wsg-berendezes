;;; S16 R15 médiafal – 3D szerkezeti modell (generálva: 2026-10-30, f2_cad_export.py)
;;; STÁTUSZ: TERVI MODELL – nem gyártási kiadás. Forrás: parts_v1.json (S16-R15-GY-v1).
;;; ActiveX (vla-*) nélkül: csak parancs + entmake – AutoCAD for Mac-en is fut.
;;; Használat: APPLOAD → ezt a fájlt → parancssor: (s16-build)   majd ellenőrzés: (s16-readback "<mappa>")
;;; Egység: mm. KOORDINÁTA: Y_CAD = -Y_helyi (egyetlen tükrözés). Az R14 helyi rendszer (X jobbra a szobából, Y faltól a szoba
;;; felé, Z fel) balkezes; jobbkezes AutoCAD-ben e nélkül a bútor tükörképe épülne. Így a fal síkja Y=0, a front -Y felé néz,
;;; az AutoCAD FRONT nézet = szobából nézett homlokzat (torony bal oldalt).

(defun s16-env ()
  (setvar "CMDECHO" 0) (setvar "OSMODE" 0) (setvar "INSUNITS" 4) (setvar "DELOBJ" 1)
  (command "_.UCS" "_W"))

(defun s16-layer (name col)
  (if (not (tblsearch "LAYER" name)) (command "_.-LAYER" "_M" name "_C" (itoa col) "" "") (command "_.-LAYER" "_S" name ""))
  (setvar "CLAYER" name))

(defun s16-box (x y z dx dy dz)
  (command "_.BOX" (list x y z) (list (+ x dx) (+ y dy) (+ z dz)))
  (entlast))

;; zárt LWPOLYLINE a WCS XY síkban; pts = ((u v bulge) ...)
(defun s16-lwpoly (pts / d)
  (setq d (list '(0 . "LWPOLYLINE") '(100 . "AcDbEntity") '(100 . "AcDbPolyline") (cons 90 (length pts)) '(70 . 1)))
  (foreach p pts (setq d (append d (list (list 10 (car p) (cadr p)) (cons 42 (caddr p))))))
  (entmake d)
  (entlast))

;; profil (U=X, V=Z) kihúzása T-vel, X körüli +90°-os forgatás: (u v n) -> (u -n v), majd tolás (x0 y0 z0)
(defun s16-extrude-y (pts tt x0 y0 z0 / pl s)
  ;; y0 itt már CAD-koordináta (= -Y_helyi), a test y0-tt .. y0 között lesz
  (setq pl (s16-lwpoly pts))
  (command "_.EXTRUDE" pl "" tt)
  (setq s (entlast))
  (command "_.ROTATE3D" s "" "_X" '(0 0 0) 90)
  (command "_.MOVE" s "" '(0 0 0) (list x0 y0 z0))
  s)

(defun s16-sub (a b) (command "_.SUBTRACT" a "" b "") a)

;; henger két pont között (tengely), r sugár – furatokhoz, tiplikhez
(defun s16-cyl (x y z r x2 y2 z2) (command "_.CYLINDER" (list x y z) r "_A" (list x2 y2 z2)) (entlast))

(defun s16-count (pre / ss i n e)
  (setq ss (ssget "_X" '((0 . "3DSOLID"))) i 0 n 0)
  (if ss (while (< i (sslength ss)) (setq e (ssname ss i)) (if (wcmatch (cdr (assoc 8 (entget e))) (strcat pre "*")) (setq n (1+ n))) (setq i (1+ i))))
  n)

(defun s16-copy (e / last) (setq last (entlast)) (command "_.COPY" e "" '(0 0 0) '(0 0 0)) (entlast))

(defun s16-safe (s / r i c)
  ;; fájlnévhez: $ és # → _ (vl-string-* nélkül, Mac-kompatibilis)
  (setq r "" i 1)
  (while (<= i (strlen s))
    (setq c (substr s i 1))
    (setq r (strcat r (if (member c '("$" "#")) "_" c)) i (1+ i)))
  r)

(defun s16-readback (dir / ss i e lay n)
  ;; minden $PART_ 3D test MASSPROP-ja külön fájlba: <dir>/<réteg>.mpr (AutoCAD tömegjellemző-szöveg, NEM woodWOP MPR)
  (setvar "FILEDIA" 0)
  (setq ss (ssget "_X" '((0 . "3DSOLID"))) i 0 n 0)
  (if ss
    (while (< i (sslength ss))
      (setq e (ssname ss i) lay (cdr (assoc 8 (entget e))))
      (if (= (substr lay 1 6) "$PART_")
        (progn (command "_.MASSPROP" e "" "_Y" (strcat dir "/" (s16-safe lay))) (setq n (1+ n))))
      (setq i (1+ i))))
  (setvar "FILEDIA" 1)
  (princ (strcat "\nS16 readback: " (itoa n) " test kiirva ide: " dir))
  (princ))

(defun s16-smoketest ( / a b c)
  ;; parancs-próba a teljes build előtt: hasáb, íves (bulge) kihúzás, kivonás – várt értékek a 30_eredmenyek-ben
  (s16-env)
  (s16-layer "$PART_SMOKE_BOX#0000" 3)
  (setq a (s16-box 0 -300 0 400 18 600))
  (s16-layer "$PART_SMOKE_ARC#0000" 4)
  (setq c (s16-extrude-y (list (list 0 0 0) (list 100 0 0.414213562) (list 200 100 0) (list 200 200 0) (list 0 200 0)) 18 600 -18 0))
  (s16-layer "$PART_SMOKE_SUB#0000" 5)
  (setq a (s16-box 1000 -300 0 400 18 600))
  (setq b (s16-box 1100 -310 100 200 38 400))
  (s16-sub a b)
  (command "_.ZOOM" "_E")
  (princ "\nS16 smoketest kesz: 3 test. Futtasd: (s16-readback \"<mappa>\")")
  (princ))

(defun s16-build ( / a b)
  (s16-env)
  ;; D1-L
  (s16-layer "$PART_S16_D1-L\U+02D90\U+02D90\U+00A80V00\U+02D90\U+00A8#0\U+00A816001" 8)
  (setq a (s16-box 435 -377 168 18 337 402))
  ;; D1-R
  (s16-layer "$PART_S16_D1-R\U+02D90\U+02D90\U+00A80V00\U+02D90\U+00A8#0\U+00A816002" 8)
  (setq a (s16-box 852 -377 168 18 337 402))
  ;; D1-T
  (s16-layer "$PART_S16_D1-T\U+02D90\U+02D90\U+00A8F0F0\U+02D90\U+00A8#0\U+00A816003" 250)
  (setq a (s16-box 453 -377 552 399 337 18))
  ;; D1-BACK
  (s16-layer "$PART_S16_D1-BACK\U+02D90\U+02D90\U+00A80000\U+02D90\U+00A8#0\U+00A816004" 9)
  (setq a (s16-box 453 -48 168 399 8 384))
  ;; D1-FRONT
  (s16-layer "$PART_S16_D1-FRONT\U+02D90\U+02D90\U+00A8VVVV\U+02D90\U+00A8#0\U+00A816005" 34)
  (setq a (s16-box 436.5 -400 171 432 18 378))
  ;; D1-BOX-L
  (s16-layer "$PART_S16_D1-BOX-L\U+02D90\U+02D90\U+00A8LLLL\U+02D90\U+00A8#0\U+00A816006" 42)
  (setq a (s16-box 459 -370 210 15 290 237))
  ;; D1-BOX-R
  (s16-layer "$PART_S16_D1-BOX-R\U+02D90\U+02D90\U+00A8LLLL\U+02D90\U+00A8#0\U+00A816007" 42)
  (setq a (s16-box 831 -370 210 15 290 237))
  ;; D1-BOX-F
  (s16-layer "$PART_S16_D1-BOX-F\U+02D90\U+02D90\U+00A800L0\U+02D90\U+00A8#0\U+00A816008" 42)
  (setq a (s16-box 474 -370 237 357 15 210))
  ;; D1-BOX-H
  (s16-layer "$PART_S16_D1-BOX-H\U+02D90\U+02D90\U+00A800L0\U+02D90\U+00A8#0\U+00A816009" 42)
  (setq a (s16-box 474 -95 237 357 15 210))
  ;; D1-BOX-B
  (s16-layer "$PART_S16_D1-BOX-B\U+02D90\U+02D90\U+00A8L0L0\U+02D90\U+00A8#0\U+00A816010" 42)
  (setq a (s16-box 474 -370 222 357 290 15))
  ;; D2-L
  (s16-layer "$PART_S16_D2-L\U+02D90\U+02D90\U+00A8VVV0\U+02D90\U+00A8#0\U+00A816011" 8)
  (setq a (s16-box 870 -377 150 18 337 420))
  ;; D2-R
  (s16-layer "$PART_S16_D2-R\U+02D90\U+02D90\U+00A8VVV0\U+02D90\U+00A8#0\U+00A816012" 8)
  (setq a (s16-box 1277 -377 150 18 337 420))
  ;; D2-B
  (s16-layer "$PART_S16_D2-B\U+02D90\U+02D90\U+00A8V000\U+02D90\U+00A8#0\U+00A816013" 8)
  (setq a (s16-box 888 -377 150 389 337 18))
  ;; D2-T
  (s16-layer "$PART_S16_D2-T\U+02D90\U+02D90\U+00A8F0F0\U+02D90\U+00A8#0\U+00A816014" 250)
  (setq a (s16-box 888 -377 552 389 337 18))
  ;; D2-BACK
  (s16-layer "$PART_S16_D2-BACK\U+02D90\U+02D90\U+00A80000\U+02D90\U+00A8#0\U+00A816015" 9)
  (setq a (s16-box 888 -48 168 389 8 384))
  ;; D2-FRONT
  (s16-layer "$PART_S16_D2-FRONT\U+02D90\U+02D90\U+00A8VVVV\U+02D90\U+00A8#0\U+00A816016" 34)
  (setq a (s16-box 871.5 -400 171 422 18 378))
  ;; D2-BOX-L
  (s16-layer "$PART_S16_D2-BOX-L\U+02D90\U+02D90\U+00A8LLLL\U+02D90\U+00A8#0\U+00A816017" 42)
  (setq a (s16-box 894 -370 210 15 290 237))
  ;; D2-BOX-R
  (s16-layer "$PART_S16_D2-BOX-R\U+02D90\U+02D90\U+00A8LLLL\U+02D90\U+00A8#0\U+00A816018" 42)
  (setq a (s16-box 1256 -370 210 15 290 237))
  ;; D2-BOX-F
  (s16-layer "$PART_S16_D2-BOX-F\U+02D90\U+02D90\U+00A800L0\U+02D90\U+00A8#0\U+00A816019" 42)
  (setq a (s16-box 909 -370 237 347 15 210))
  ;; D2-BOX-H
  (s16-layer "$PART_S16_D2-BOX-H\U+02D90\U+02D90\U+00A800L0\U+02D90\U+00A8#0\U+00A816020" 42)
  (setq a (s16-box 909 -95 237 347 15 210))
  ;; D2-BOX-B
  (s16-layer "$PART_S16_D2-BOX-B\U+02D90\U+02D90\U+00A8L0L0\U+02D90\U+00A8#0\U+00A816021" 42)
  (setq a (s16-box 909 -370 222 347 290 15))
  ;; D3-L
  (s16-layer "$PART_S16_D3-L\U+02D90\U+02D90\U+00A8VVV0\U+02D90\U+00A8#0\U+00A816022" 8)
  (setq a (s16-box 1295 -377 150 18 337 420))
  ;; D3-R
  (s16-layer "$PART_S16_D3-R\U+02D90\U+02D90\U+00A8VVV0\U+02D90\U+00A8#0\U+00A816023" 8)
  (setq a (s16-box 1702 -377 150 18 337 420))
  ;; D3-B
  (s16-layer "$PART_S16_D3-B\U+02D90\U+02D90\U+00A8V000\U+02D90\U+00A8#0\U+00A816024" 8)
  (setq a (s16-box 1313 -377 150 389 337 18))
  ;; D3-T
  (s16-layer "$PART_S16_D3-T\U+02D90\U+02D90\U+00A8F0F0\U+02D90\U+00A8#0\U+00A816025" 250)
  (setq a (s16-box 1313 -377 552 389 337 18))
  ;; D3-BACK
  (s16-layer "$PART_S16_D3-BACK\U+02D90\U+02D90\U+00A80000\U+02D90\U+00A8#0\U+00A816026" 9)
  (setq a (s16-box 1313 -48 168 389 8 384))
  ;; D3-FRONT
  (s16-layer "$PART_S16_D3-FRONT\U+02D90\U+02D90\U+00A8VVVV\U+02D90\U+00A8#0\U+00A816027" 34)
  (setq a (s16-box 1296.5 -400 171 422 18 378))
  ;; D3-BOX-L
  (s16-layer "$PART_S16_D3-BOX-L\U+02D90\U+02D90\U+00A8LLLL\U+02D90\U+00A8#0\U+00A816028" 42)
  (setq a (s16-box 1319 -370 210 15 290 237))
  ;; D3-BOX-R
  (s16-layer "$PART_S16_D3-BOX-R\U+02D90\U+02D90\U+00A8LLLL\U+02D90\U+00A8#0\U+00A816029" 42)
  (setq a (s16-box 1681 -370 210 15 290 237))
  ;; D3-BOX-F
  (s16-layer "$PART_S16_D3-BOX-F\U+02D90\U+02D90\U+00A800L0\U+02D90\U+00A8#0\U+00A816030" 42)
  (setq a (s16-box 1334 -370 237 347 15 210))
  ;; D3-BOX-H
  (s16-layer "$PART_S16_D3-BOX-H\U+02D90\U+02D90\U+00A800L0\U+02D90\U+00A8#0\U+00A816031" 42)
  (setq a (s16-box 1334 -95 237 347 15 210))
  ;; D3-BOX-B
  (s16-layer "$PART_S16_D3-BOX-B\U+02D90\U+02D90\U+00A8L0L0\U+02D90\U+00A8#0\U+00A816032" 42)
  (setq a (s16-box 1334 -370 222 347 290 15))
  ;; D4-L
  (s16-layer "$PART_S16_D4-L\U+02D90\U+02D90\U+00A8VVV0\U+02D90\U+00A8#0\U+00A816033" 8)
  (setq a (s16-box 1720 -377 150 18 337 420))
  ;; D4-R
  (s16-layer "$PART_S16_D4-R\U+02D90\U+02D90\U+00A8VVV0\U+02D90\U+00A8#0\U+00A816034" 8)
  (setq a (s16-box 2732 -377 150 18 337 420))
  ;; D4-B
  (s16-layer "$PART_S16_D4-B\U+02D90\U+02D90\U+00A8V000\U+02D90\U+00A8#0\U+00A816035" 8)
  (setq a (s16-box 1738 -377 150 994 337 18))
  ;; D4-T
  (s16-layer "$PART_S16_D4-T\U+02D90\U+02D90\U+00A8F0F0\U+02D90\U+00A8#0\U+00A816036" 250)
  (setq a (s16-box 1738 -377 552 994 337 18))
  ;; D4-BACK
  (s16-layer "$PART_S16_D4-BACK\U+02D90\U+02D90\U+00A80000\U+02D90\U+00A8#0\U+00A816037" 9)
  (setq a (s16-box 1738 -48 168 994 8 384))
  ;; D4-FRONT
  (s16-layer "$PART_S16_D4-FRONT\U+02D90\U+02D90\U+00A8VVVV\U+02D90\U+00A8#0\U+00A816038" 34)
  (setq a (s16-box 1721.5 -400 171 1027 18 378))
  ;; D4-BOX-L
  (s16-layer "$PART_S16_D4-BOX-L\U+02D90\U+02D90\U+00A8LLLL\U+02D90\U+00A8#0\U+00A816039" 42)
  (setq a (s16-box 1744 -370 210 15 290 237))
  ;; D4-BOX-R
  (s16-layer "$PART_S16_D4-BOX-R\U+02D90\U+02D90\U+00A8LLLL\U+02D90\U+00A8#0\U+00A816040" 42)
  (setq a (s16-box 2711 -370 210 15 290 237))
  ;; D4-BOX-F
  (s16-layer "$PART_S16_D4-BOX-F\U+02D90\U+02D90\U+00A800L0\U+02D90\U+00A8#0\U+00A816041" 42)
  (setq a (s16-box 1759 -370 237 952 15 210))
  ;; D4-BOX-H
  (s16-layer "$PART_S16_D4-BOX-H\U+02D90\U+02D90\U+00A800L0\U+02D90\U+00A8#0\U+00A816042" 42)
  (setq a (s16-box 1759 -95 237 952 15 210))
  ;; D4-BOX-B
  (s16-layer "$PART_S16_D4-BOX-B\U+02D90\U+02D90\U+00A8L0L0\U+02D90\U+00A8#0\U+00A816043" 42)
  (setq a (s16-box 1759 -370 222 952 290 15))
  ;; D5-L
  (s16-layer "$PART_S16_D5-L\U+02D90\U+02D90\U+00A8VVV0\U+02D90\U+00A8#0\U+00A816044" 8)
  (setq a (s16-box 2750 -377 150 18 337 420))
  ;; D5-R
  (s16-layer "$PART_S16_D5-R\U+02D90\U+02D90\U+00A8VVV0\U+02D90\U+00A8#0\U+00A816045" 8)
  (setq a (s16-box 3157 -377 150 18 337 420))
  ;; D5-B
  (s16-layer "$PART_S16_D5-B\U+02D90\U+02D90\U+00A8V000\U+02D90\U+00A8#0\U+00A816046" 8)
  (setq a (s16-box 2768 -377 150 389 337 18))
  ;; D5-T
  (s16-layer "$PART_S16_D5-T\U+02D90\U+02D90\U+00A8F0F0\U+02D90\U+00A8#0\U+00A816047" 250)
  (setq a (s16-box 2768 -377 552 389 337 18))
  ;; D5-BACK
  (s16-layer "$PART_S16_D5-BACK\U+02D90\U+02D90\U+00A80000\U+02D90\U+00A8#0\U+00A816048" 9)
  (setq a (s16-box 2768 -48 168 389 8 384))
  ;; D5-FRONT
  (s16-layer "$PART_S16_D5-FRONT\U+02D90\U+02D90\U+00A8VVVV\U+02D90\U+00A8#0\U+00A816049" 34)
  (setq a (s16-box 2751.5 -400 171 422 18 378))
  ;; D5-BOX-L
  (s16-layer "$PART_S16_D5-BOX-L\U+02D90\U+02D90\U+00A8LLLL\U+02D90\U+00A8#0\U+00A816050" 42)
  (setq a (s16-box 2774 -370 210 15 290 237))
  ;; D5-BOX-R
  (s16-layer "$PART_S16_D5-BOX-R\U+02D90\U+02D90\U+00A8LLLL\U+02D90\U+00A8#0\U+00A816051" 42)
  (setq a (s16-box 3136 -370 210 15 290 237))
  ;; D5-BOX-F
  (s16-layer "$PART_S16_D5-BOX-F\U+02D90\U+02D90\U+00A800L0\U+02D90\U+00A8#0\U+00A816052" 42)
  (setq a (s16-box 2789 -370 237 347 15 210))
  ;; D5-BOX-H
  (s16-layer "$PART_S16_D5-BOX-H\U+02D90\U+02D90\U+00A800L0\U+02D90\U+00A8#0\U+00A816053" 42)
  (setq a (s16-box 2789 -95 237 347 15 210))
  ;; D5-BOX-B
  (s16-layer "$PART_S16_D5-BOX-B\U+02D90\U+02D90\U+00A8L0L0\U+02D90\U+00A8#0\U+00A816054" 42)
  (setq a (s16-box 2789 -370 222 347 290 15))
  ;; D6-L
  (s16-layer "$PART_S16_D6-L\U+02D90\U+02D90\U+00A8VVV0\U+02D90\U+00A8#0\U+00A816055" 8)
  (setq a (s16-box 3175 -377 150 18 337 420))
  ;; D6-R
  (s16-layer "$PART_S16_D6-R\U+02D90\U+02D90\U+00A80F0F\U+02D90\U+00A8#0\U+00A816056" 250)
  (setq a (s16-box 3582 -377 230 18 337 260))
  ;; D6-B
  (s16-layer "$PART_S16_D6-B\U+02D90\U+02D90\U+00A8V000\U+02D90\U+00A8#0\U+00A816057" 8)
  (setq a (s16-box 3193 -377 150 327 337 18))
  ;; D6-T
  (s16-layer "$PART_S16_D6-T\U+02D90\U+02D90\U+00A8F0F0\U+02D90\U+00A8#0\U+00A816058" 250)
  (setq a (s16-box 3193 -377 552 327 337 18))
  ;; D6-BACK
  (s16-layer "$PART_S16_D6-BACK\U+02D90\U+02D90\U+00A80000\U+02D90\U+00A8#0\U+00A816059" 9)
  (setq s16p nil)
  (setq s16p (append s16p (list (list 0.0000 0.0000 0.000000000) (list 327.0000 0.0000 0.414213562) (list 389.0000 62.0000 0.000000000) (list 389.0000 322.0000 0.414213562) (list 327.0000 384.0000 0.000000000) (list 0.0000 384.0000 0.000000000))))
  (setq a (s16-extrude-y s16p 8 3193 -40 168))
  ;; D6-FRONT
  (s16-layer "$PART_S16_D6-FRONT\U+02D90\U+02D90\U+00A8VVVV\U+02D90\U+00A8#0\U+00A816060" 34)
  (setq s16p nil)
  (setq s16p (append s16p (list (list 0.0000 0.0000 0.000000000) (list 343.5000 0.0000 0.414213562) (list 402.5000 59.0000 0.000000000) (list 402.5000 319.0000 0.414213562) (list 343.5000 378.0000 0.000000000) (list 0.0000 378.0000 0.000000000))))
  (setq a (s16-extrude-y s16p 18 3176.5 -382 171))
  ;; D6-BOX-L
  (s16-layer "$PART_S16_D6-BOX-L\U+02D90\U+02D90\U+00A8LLLL\U+02D90\U+00A8#0\U+00A816061" 42)
  (setq a (s16-box 3199 -370 210 15 290 237))
  ;; D6-BOX-R
  (s16-layer "$PART_S16_D6-BOX-R\U+02D90\U+02D90\U+00A8LLLL\U+02D90\U+00A8#0\U+00A816062" 42)
  (setq a (s16-box 3561 -370 210 15 290 237))
  ;; D6-BOX-F
  (s16-layer "$PART_S16_D6-BOX-F\U+02D90\U+02D90\U+00A800L0\U+02D90\U+00A8#0\U+00A816063" 42)
  (setq a (s16-box 3214 -370 237 347 15 210))
  ;; D6-BOX-H
  (s16-layer "$PART_S16_D6-BOX-H\U+02D90\U+02D90\U+00A800L0\U+02D90\U+00A8#0\U+00A816064" 42)
  (setq a (s16-box 3214 -95 237 347 15 210))
  ;; D6-BOX-B
  (s16-layer "$PART_S16_D6-BOX-B\U+02D90\U+02D90\U+00A8L0L0\U+02D90\U+00A8#0\U+00A816065" 42)
  (setq a (s16-box 3214 -370 222 347 290 15))
  ;; T-L
  (s16-layer "$PART_S16_T-L\U+02D90\U+02D90\U+00A80V00\U+02D90\U+00A8#0\U+00A816066" 8)
  (setq a (s16-box 0 -377 250 18 337 2525))
  ;; T-R
  (s16-layer "$PART_S16_T-R\U+02D90\U+02D90\U+00A80F0F\U+02D90\U+00A8#0\U+00A816067" 250)
  (setq a (s16-box 852 -377 570 18 337 2205))
  ;; T-B
  (s16-layer "TECH_KIMETSZES_S16_T-B" 1)
  (setq b (s16-box 37 -378 569 380 28 20))
  (s16-layer "$PART_S16_T-B\U+02D90\U+02D90\U+00A8V000\U+02D90\U+00A8#0\U+00A816068" 8)
  (setq a (s16-box 18 -377 570 834 337 18))
  (s16-layer "$PART_S16_T-B\U+02D90\U+02D90\U+00A8V000\U+02D90\U+00A8#0\U+00A816068" 8)
  (setq b (s16-box 37 -378 569 380 28 20))
  (s16-sub a b)
  ;; T-C
  (s16-layer "$PART_S16_T-C\U+02D90\U+02D90\U+00A80V00\U+02D90\U+00A8#0\U+00A816069" 8)
  (setq a (s16-box 426 -377 588 18 337 2269))
  ;; T-L-S1
  (s16-layer "$PART_S16_T-L-S1\U+02D90\U+02D90\U+00A8V000\U+02D90\U+00A8#0\U+00A816070" 8)
  (setq a (s16-box 19 -340 935 406 290 18))
  ;; T-L-S2
  (s16-layer "$PART_S16_T-L-S2\U+02D90\U+02D90\U+00A8V000\U+02D90\U+00A8#0\U+00A816071" 8)
  (setq a (s16-box 19 -340 1320 406 290 18))
  ;; T-L-S3
  (s16-layer "$PART_S16_T-L-S3\U+02D90\U+02D90\U+00A8V000\U+02D90\U+00A8#0\U+00A816072" 8)
  (setq a (s16-box 19 -340 1705 406 290 18))
  ;; T-L-S4
  (s16-layer "$PART_S16_T-L-S4\U+02D90\U+02D90\U+00A8V000\U+02D90\U+00A8#0\U+00A816073" 8)
  (setq a (s16-box 19 -340 2090 406 290 18))
  ;; T-L-S5
  (s16-layer "$PART_S16_T-L-S5\U+02D90\U+02D90\U+00A8V000\U+02D90\U+00A8#0\U+00A816074" 8)
  (setq a (s16-box 19 -340 2475 406 290 18))
  ;; T-L-BACK
  (s16-layer "$PART_S16_T-L-BACK\U+02D90\U+02D90\U+00A80000\U+02D90\U+00A8#0\U+00A816075" 9)
  (setq s16p nil)
  (setq s16p (append s16p (list (list 0.0000 0.0000 0.000000000) (list 406.0000 0.0000 0.000000000) (list 406.0000 1921.0000 0.000000000) (list 81.0000 1921.0000 0.357805721) (list 0.5756 1854.9974 0.000000000) (list 0.0000 1851.6801 0.000000000))))
  (setq a (s16-extrude-y s16p 8 19 -40 935))
  ;; T-L-SERVICE
  (s16-layer "$PART_S16_T-L-SERVICE\U+02D90\U+02D90\U+00A8VVVV\U+02D90\U+00A8#0\U+00A816076" 9)
  (setq a (s16-box 19 -135 589 406 8 345))
  ;; T-R-S1
  (s16-layer "$PART_S16_T-R-S1\U+02D90\U+02D90\U+00A8V000\U+02D90\U+00A8#0\U+00A816077" 8)
  (setq a (s16-box 445 -340 935 406 290 18))
  ;; T-R-S2
  (s16-layer "$PART_S16_T-R-S2\U+02D90\U+02D90\U+00A8V000\U+02D90\U+00A8#0\U+00A816078" 8)
  (setq a (s16-box 445 -340 1320 406 290 18))
  ;; T-R-S3
  (s16-layer "$PART_S16_T-R-S3\U+02D90\U+02D90\U+00A8V000\U+02D90\U+00A8#0\U+00A816079" 8)
  (setq a (s16-box 445 -340 1705 406 290 18))
  ;; T-R-S4
  (s16-layer "$PART_S16_T-R-S4\U+02D90\U+02D90\U+00A8V000\U+02D90\U+00A8#0\U+00A816080" 8)
  (setq a (s16-box 445 -340 2090 406 290 18))
  ;; T-R-S5
  (s16-layer "$PART_S16_T-R-S5\U+02D90\U+02D90\U+00A8V000\U+02D90\U+00A8#0\U+00A816081" 8)
  (setq a (s16-box 445 -340 2475 406 290 18))
  ;; T-R-BACK
  (s16-layer "$PART_S16_T-R-BACK\U+02D90\U+02D90\U+00A80000\U+02D90\U+00A8#0\U+00A816082" 9)
  (setq s16p nil)
  (setq s16p (append s16p (list (list 0.0000 0.0000 0.000000000) (list 406.0000 0.0000 0.000000000) (list 406.0000 1851.6801 0.000000000) (list 405.4244 1854.9974 0.357805721) (list 325.0000 1921.0000 0.000000000) (list 0.0000 1921.0000 0.000000000))))
  (setq a (s16-extrude-y s16p 8 445 -40 935))
  ;; T-R-SERVICE
  (s16-layer "$PART_S16_T-R-SERVICE\U+02D90\U+02D90\U+00A8VVVV\U+02D90\U+00A8#0\U+00A816083" 9)
  (setq a (s16-box 445 -135 589 406 8 345))
  ;; T-DOOR-L
  (s16-layer "TECH_ATMENO_KIVAGAS_S16_T-DOOR-L" 1)
  (setq s16p nil)
  (setq s16p (append s16p (list (list 326.0000 89.0000 0.000000000) (list 328.6987 89.0662 0.000000000) (list 331.3909 89.2648 0.000000000) (list 334.0702 89.5953 0.000000000) (list 336.7300 90.0568 0.000000000) (list 339.3639 90.6483 0.000000000) (list 341.9657 91.3683 0.000000000) (list 344.5289 92.2151 0.000000000) (list 347.0476 93.1866 0.000000000) (list 349.5155 94.2806 0.000000000) (list 351.9268 95.4943 0.000000000) (list 354.2757 96.8249 0.000000000) (list 356.5564 98.2692 0.000000000) (list 358.7635 99.8236 0.000000000) (list 360.8916 101.4844 0.000000000) (list 362.9357 103.2477 0.000000000) (list 364.8909 105.1091 0.000000000) (list 366.7523 107.0643 0.000000000) (list 368.5156 109.1084 0.000000000) (list 370.1764 111.2365 0.000000000) (list 371.7308 113.4436 0.000000000) (list 373.1751 115.7243 0.000000000) (list 374.5057 118.0732 0.000000000) (list 375.7194 120.4845 0.000000000) (list 376.8134 122.9524 0.000000000) (list 377.7849 125.4711 0.000000000) (list 378.6317 128.0343 0.000000000) (list 379.3517 130.6361 0.000000000) (list 379.9432 133.2700 0.000000000) (list 380.4047 135.9298 0.000000000) (list 380.7352 138.6091 0.000000000) (list 380.9338 141.3013 0.000000000) (list 381.0000 144.0000 0.000000000) (list 381.0000 2539.0000 0.000000000) (list 380.9338 2541.6987 0.000000000) (list 380.7352 2544.3909 0.000000000) (list 380.4047 2547.0702 0.000000000) (list 379.9432 2549.7300 0.000000000) (list 379.3517 2552.3639 0.000000000) (list 378.6317 2554.9657 0.000000000))))
  (setq s16p (append s16p (list (list 377.7849 2557.5289 0.000000000) (list 376.8134 2560.0476 0.000000000) (list 375.7194 2562.5155 0.000000000) (list 374.5057 2564.9268 0.000000000) (list 373.1751 2567.2757 0.000000000) (list 371.7308 2569.5564 0.000000000) (list 370.1764 2571.7635 0.000000000) (list 368.5156 2573.8916 0.000000000) (list 366.7523 2575.9357 0.000000000) (list 364.8909 2577.8909 0.000000000) (list 362.9357 2579.7523 0.000000000) (list 360.8916 2581.5156 0.000000000) (list 358.7635 2583.1764 0.000000000) (list 356.5564 2584.7308 0.000000000) (list 354.2757 2586.1751 0.000000000) (list 351.9268 2587.5057 0.000000000) (list 349.5155 2588.7194 0.000000000) (list 347.0476 2589.8134 0.000000000) (list 344.5289 2590.7849 0.000000000) (list 341.9657 2591.6317 0.000000000) (list 339.3639 2592.3517 0.000000000) (list 336.7300 2592.9432 0.000000000) (list 334.0702 2593.4047 0.000000000) (list 331.3909 2593.7352 0.000000000) (list 328.6987 2593.9338 0.000000000) (list 326.0000 2594.0000 0.000000000) (list 86.0000 2594.0000 0.000000000) (list 83.3013 2593.9338 0.000000000) (list 80.6091 2593.7352 0.000000000) (list 77.9298 2593.4047 0.000000000) (list 75.2700 2592.9432 0.000000000) (list 72.6361 2592.3517 0.000000000) (list 70.0343 2591.6317 0.000000000) (list 67.4711 2590.7849 0.000000000) (list 64.9524 2589.8134 0.000000000) (list 62.4845 2588.7194 0.000000000) (list 60.0732 2587.5057 0.000000000) (list 57.7243 2586.1751 0.000000000) (list 55.4436 2584.7308 0.000000000) (list 53.2365 2583.1764 0.000000000))))
  (setq s16p (append s16p (list (list 51.1084 2581.5156 0.000000000) (list 49.0643 2579.7523 0.000000000) (list 47.1091 2577.8909 0.000000000) (list 45.2477 2575.9357 0.000000000) (list 43.4844 2573.8916 0.000000000) (list 41.8236 2571.7635 0.000000000) (list 40.2692 2569.5564 0.000000000) (list 38.8249 2567.2757 0.000000000) (list 37.4943 2564.9268 0.000000000) (list 36.2806 2562.5155 0.000000000) (list 35.1866 2560.0476 0.000000000) (list 34.2151 2557.5289 0.000000000) (list 33.3683 2554.9657 0.000000000) (list 32.6483 2552.3639 0.000000000) (list 32.0568 2549.7300 0.000000000) (list 31.5953 2547.0702 0.000000000) (list 31.2648 2544.3909 0.000000000) (list 31.0662 2541.6987 0.000000000) (list 31.0000 2539.0000 0.000000000) (list 31.0000 144.0000 0.000000000) (list 31.0662 141.3013 0.000000000) (list 31.2648 138.6091 0.000000000) (list 31.5953 135.9298 0.000000000) (list 32.0568 133.2700 0.000000000) (list 32.6483 130.6361 0.000000000) (list 33.3683 128.0343 0.000000000) (list 34.2151 125.4711 0.000000000) (list 35.1866 122.9524 0.000000000) (list 36.2806 120.4845 0.000000000) (list 37.4943 118.0732 0.000000000) (list 38.8249 115.7243 0.000000000) (list 40.2692 113.4436 0.000000000) (list 41.8236 111.2365 0.000000000) (list 43.4844 109.1084 0.000000000) (list 45.2477 107.0643 0.000000000) (list 47.1091 105.1091 0.000000000) (list 49.0643 103.2477 0.000000000) (list 51.1084 101.4844 0.000000000) (list 53.2365 99.8236 0.000000000) (list 55.4436 98.2692 0.000000000))))
  (setq s16p (append s16p (list (list 57.7243 96.8249 0.000000000) (list 60.0732 95.4943 0.000000000) (list 62.4845 94.2806 0.000000000) (list 64.9524 93.1866 0.000000000) (list 67.4711 92.2151 0.000000000) (list 70.0343 91.3683 0.000000000) (list 72.6361 90.6483 0.000000000) (list 75.2700 90.0568 0.000000000) (list 77.9298 89.5953 0.000000000) (list 80.6091 89.2648 0.000000000) (list 83.3013 89.0662 0.000000000) (list 86.0000 89.0000 0.000000000))))
  (setq b (s16-extrude-y s16p 20 21 -381 171))
  (s16-layer "TECH_HATSO_FENYFALC_S16_T-DOOR-L" 1)
  (setq s16p nil)
  (setq s16p (append s16p (list (list 326.0000 83.0000 0.000000000) (list 328.9931 83.0735 0.000000000) (list 331.9790 83.2937 0.000000000) (list 334.9506 83.6602 0.000000000) (list 337.9005 84.1721 0.000000000) (list 340.8218 84.8281 0.000000000) (list 343.7074 85.6266 0.000000000) (list 346.5503 86.5658 0.000000000) (list 349.3437 87.6433 0.000000000) (list 352.0809 88.8567 0.000000000) (list 354.7552 90.2028 0.000000000) (list 357.3603 91.6786 0.000000000) (list 359.8898 93.2804 0.000000000) (list 362.3377 95.0043 0.000000000) (list 364.6980 96.8464 0.000000000) (list 366.9651 98.8020 0.000000000) (list 369.1335 100.8665 0.000000000) (list 371.1980 103.0349 0.000000000) (list 373.1536 105.3020 0.000000000) (list 374.9957 107.6623 0.000000000) (list 376.7196 110.1102 0.000000000) (list 378.3214 112.6397 0.000000000) (list 379.7972 115.2448 0.000000000) (list 381.1433 117.9191 0.000000000) (list 382.3567 120.6563 0.000000000) (list 383.4342 123.4497 0.000000000) (list 384.3734 126.2926 0.000000000) (list 385.1719 129.1782 0.000000000) (list 385.8279 132.0995 0.000000000) (list 386.3398 135.0494 0.000000000) (list 386.7063 138.0210 0.000000000) (list 386.9265 141.0069 0.000000000) (list 387.0000 144.0000 0.000000000) (list 387.0000 2539.0000 0.000000000) (list 386.9265 2541.9931 0.000000000) (list 386.7063 2544.9790 0.000000000) (list 386.3398 2547.9506 0.000000000) (list 385.8279 2550.9005 0.000000000) (list 385.1719 2553.8218 0.000000000) (list 384.3734 2556.7074 0.000000000))))
  (setq s16p (append s16p (list (list 383.4342 2559.5503 0.000000000) (list 382.3567 2562.3437 0.000000000) (list 381.1433 2565.0809 0.000000000) (list 379.7972 2567.7552 0.000000000) (list 378.3214 2570.3603 0.000000000) (list 376.7196 2572.8898 0.000000000) (list 374.9957 2575.3377 0.000000000) (list 373.1536 2577.6980 0.000000000) (list 371.1980 2579.9651 0.000000000) (list 369.1335 2582.1335 0.000000000) (list 366.9651 2584.1980 0.000000000) (list 364.6980 2586.1536 0.000000000) (list 362.3377 2587.9957 0.000000000) (list 359.8898 2589.7196 0.000000000) (list 357.3603 2591.3214 0.000000000) (list 354.7552 2592.7972 0.000000000) (list 352.0809 2594.1433 0.000000000) (list 349.3437 2595.3567 0.000000000) (list 346.5503 2596.4342 0.000000000) (list 343.7074 2597.3734 0.000000000) (list 340.8218 2598.1719 0.000000000) (list 337.9005 2598.8279 0.000000000) (list 334.9506 2599.3398 0.000000000) (list 331.9790 2599.7063 0.000000000) (list 328.9931 2599.9265 0.000000000) (list 326.0000 2600.0000 0.000000000) (list 86.0000 2600.0000 0.000000000) (list 83.0069 2599.9265 0.000000000) (list 80.0210 2599.7063 0.000000000) (list 77.0494 2599.3398 0.000000000) (list 74.0995 2598.8279 0.000000000) (list 71.1782 2598.1719 0.000000000) (list 68.2926 2597.3734 0.000000000) (list 65.4497 2596.4342 0.000000000) (list 62.6563 2595.3567 0.000000000) (list 59.9191 2594.1433 0.000000000) (list 57.2448 2592.7972 0.000000000) (list 54.6397 2591.3214 0.000000000) (list 52.1102 2589.7196 0.000000000) (list 49.6623 2587.9957 0.000000000))))
  (setq s16p (append s16p (list (list 47.3020 2586.1536 0.000000000) (list 45.0349 2584.1980 0.000000000) (list 42.8665 2582.1335 0.000000000) (list 40.8020 2579.9651 0.000000000) (list 38.8464 2577.6980 0.000000000) (list 37.0043 2575.3377 0.000000000) (list 35.2804 2572.8898 0.000000000) (list 33.6786 2570.3603 0.000000000) (list 32.2028 2567.7552 0.000000000) (list 30.8567 2565.0809 0.000000000) (list 29.6433 2562.3437 0.000000000) (list 28.5658 2559.5503 0.000000000) (list 27.6266 2556.7074 0.000000000) (list 26.8281 2553.8218 0.000000000) (list 26.1721 2550.9005 0.000000000) (list 25.6602 2547.9506 0.000000000) (list 25.2937 2544.9790 0.000000000) (list 25.0735 2541.9931 0.000000000) (list 25.0000 2539.0000 0.000000000) (list 25.0000 144.0000 0.000000000) (list 25.0735 141.0069 0.000000000) (list 25.2937 138.0210 0.000000000) (list 25.6602 135.0494 0.000000000) (list 26.1721 132.0995 0.000000000) (list 26.8281 129.1782 0.000000000) (list 27.6266 126.2926 0.000000000) (list 28.5658 123.4497 0.000000000) (list 29.6433 120.6563 0.000000000) (list 30.8567 117.9191 0.000000000) (list 32.2028 115.2448 0.000000000) (list 33.6786 112.6397 0.000000000) (list 35.2804 110.1102 0.000000000) (list 37.0043 107.6623 0.000000000) (list 38.8464 105.3020 0.000000000) (list 40.8020 103.0349 0.000000000) (list 42.8665 100.8665 0.000000000) (list 45.0349 98.8020 0.000000000) (list 47.3020 96.8464 0.000000000) (list 49.6623 95.0043 0.000000000) (list 52.1102 93.2804 0.000000000))))
  (setq s16p (append s16p (list (list 54.6397 91.6786 0.000000000) (list 57.2448 90.2028 0.000000000) (list 59.9191 88.8567 0.000000000) (list 62.6563 87.6433 0.000000000) (list 65.4497 86.5658 0.000000000) (list 68.2926 85.6266 0.000000000) (list 71.1782 84.8281 0.000000000) (list 74.0995 84.1721 0.000000000) (list 77.0494 83.6602 0.000000000) (list 80.0210 83.2937 0.000000000) (list 83.0069 83.0735 0.000000000) (list 86.0000 83.0000 0.000000000))))
  (setq b (s16-extrude-y s16p 11 21 -381 171))
  (s16-layer "$PART_S16_T-DOOR-L\U+02D90\U+02D90\U+00A8VVVV\U+02D90\U+00A8#0\U+00A816084" 34)
  (setq s16p nil)
  (setq s16p (append s16p (list (list 79.0000 0.0000 0.000000000) (list 412.5000 0.0000 0.000000000) (list 412.5000 2683.0000 0.000000000) (list 79.0000 2683.0000 0.414213562) (list 0.0000 2604.0000 0.000000000) (list 0.0000 79.0000 0.414213562))))
  (setq a (s16-extrude-y s16p 18 21 -382 171))
  (s16-layer "$PART_S16_T-DOOR-L\U+02D90\U+02D90\U+00A8VVVV\U+02D90\U+00A8#0\U+00A816084" 34)
  (setq s16p nil)
  (setq s16p (append s16p (list (list 326.0000 89.0000 0.000000000) (list 328.6987 89.0662 0.000000000) (list 331.3909 89.2648 0.000000000) (list 334.0702 89.5953 0.000000000) (list 336.7300 90.0568 0.000000000) (list 339.3639 90.6483 0.000000000) (list 341.9657 91.3683 0.000000000) (list 344.5289 92.2151 0.000000000) (list 347.0476 93.1866 0.000000000) (list 349.5155 94.2806 0.000000000) (list 351.9268 95.4943 0.000000000) (list 354.2757 96.8249 0.000000000) (list 356.5564 98.2692 0.000000000) (list 358.7635 99.8236 0.000000000) (list 360.8916 101.4844 0.000000000) (list 362.9357 103.2477 0.000000000) (list 364.8909 105.1091 0.000000000) (list 366.7523 107.0643 0.000000000) (list 368.5156 109.1084 0.000000000) (list 370.1764 111.2365 0.000000000) (list 371.7308 113.4436 0.000000000) (list 373.1751 115.7243 0.000000000) (list 374.5057 118.0732 0.000000000) (list 375.7194 120.4845 0.000000000) (list 376.8134 122.9524 0.000000000) (list 377.7849 125.4711 0.000000000) (list 378.6317 128.0343 0.000000000) (list 379.3517 130.6361 0.000000000) (list 379.9432 133.2700 0.000000000) (list 380.4047 135.9298 0.000000000) (list 380.7352 138.6091 0.000000000) (list 380.9338 141.3013 0.000000000) (list 381.0000 144.0000 0.000000000) (list 381.0000 2539.0000 0.000000000) (list 380.9338 2541.6987 0.000000000) (list 380.7352 2544.3909 0.000000000) (list 380.4047 2547.0702 0.000000000) (list 379.9432 2549.7300 0.000000000) (list 379.3517 2552.3639 0.000000000) (list 378.6317 2554.9657 0.000000000))))
  (setq s16p (append s16p (list (list 377.7849 2557.5289 0.000000000) (list 376.8134 2560.0476 0.000000000) (list 375.7194 2562.5155 0.000000000) (list 374.5057 2564.9268 0.000000000) (list 373.1751 2567.2757 0.000000000) (list 371.7308 2569.5564 0.000000000) (list 370.1764 2571.7635 0.000000000) (list 368.5156 2573.8916 0.000000000) (list 366.7523 2575.9357 0.000000000) (list 364.8909 2577.8909 0.000000000) (list 362.9357 2579.7523 0.000000000) (list 360.8916 2581.5156 0.000000000) (list 358.7635 2583.1764 0.000000000) (list 356.5564 2584.7308 0.000000000) (list 354.2757 2586.1751 0.000000000) (list 351.9268 2587.5057 0.000000000) (list 349.5155 2588.7194 0.000000000) (list 347.0476 2589.8134 0.000000000) (list 344.5289 2590.7849 0.000000000) (list 341.9657 2591.6317 0.000000000) (list 339.3639 2592.3517 0.000000000) (list 336.7300 2592.9432 0.000000000) (list 334.0702 2593.4047 0.000000000) (list 331.3909 2593.7352 0.000000000) (list 328.6987 2593.9338 0.000000000) (list 326.0000 2594.0000 0.000000000) (list 86.0000 2594.0000 0.000000000) (list 83.3013 2593.9338 0.000000000) (list 80.6091 2593.7352 0.000000000) (list 77.9298 2593.4047 0.000000000) (list 75.2700 2592.9432 0.000000000) (list 72.6361 2592.3517 0.000000000) (list 70.0343 2591.6317 0.000000000) (list 67.4711 2590.7849 0.000000000) (list 64.9524 2589.8134 0.000000000) (list 62.4845 2588.7194 0.000000000) (list 60.0732 2587.5057 0.000000000) (list 57.7243 2586.1751 0.000000000) (list 55.4436 2584.7308 0.000000000) (list 53.2365 2583.1764 0.000000000))))
  (setq s16p (append s16p (list (list 51.1084 2581.5156 0.000000000) (list 49.0643 2579.7523 0.000000000) (list 47.1091 2577.8909 0.000000000) (list 45.2477 2575.9357 0.000000000) (list 43.4844 2573.8916 0.000000000) (list 41.8236 2571.7635 0.000000000) (list 40.2692 2569.5564 0.000000000) (list 38.8249 2567.2757 0.000000000) (list 37.4943 2564.9268 0.000000000) (list 36.2806 2562.5155 0.000000000) (list 35.1866 2560.0476 0.000000000) (list 34.2151 2557.5289 0.000000000) (list 33.3683 2554.9657 0.000000000) (list 32.6483 2552.3639 0.000000000) (list 32.0568 2549.7300 0.000000000) (list 31.5953 2547.0702 0.000000000) (list 31.2648 2544.3909 0.000000000) (list 31.0662 2541.6987 0.000000000) (list 31.0000 2539.0000 0.000000000) (list 31.0000 144.0000 0.000000000) (list 31.0662 141.3013 0.000000000) (list 31.2648 138.6091 0.000000000) (list 31.5953 135.9298 0.000000000) (list 32.0568 133.2700 0.000000000) (list 32.6483 130.6361 0.000000000) (list 33.3683 128.0343 0.000000000) (list 34.2151 125.4711 0.000000000) (list 35.1866 122.9524 0.000000000) (list 36.2806 120.4845 0.000000000) (list 37.4943 118.0732 0.000000000) (list 38.8249 115.7243 0.000000000) (list 40.2692 113.4436 0.000000000) (list 41.8236 111.2365 0.000000000) (list 43.4844 109.1084 0.000000000) (list 45.2477 107.0643 0.000000000) (list 47.1091 105.1091 0.000000000) (list 49.0643 103.2477 0.000000000) (list 51.1084 101.4844 0.000000000) (list 53.2365 99.8236 0.000000000) (list 55.4436 98.2692 0.000000000))))
  (setq s16p (append s16p (list (list 57.7243 96.8249 0.000000000) (list 60.0732 95.4943 0.000000000) (list 62.4845 94.2806 0.000000000) (list 64.9524 93.1866 0.000000000) (list 67.4711 92.2151 0.000000000) (list 70.0343 91.3683 0.000000000) (list 72.6361 90.6483 0.000000000) (list 75.2700 90.0568 0.000000000) (list 77.9298 89.5953 0.000000000) (list 80.6091 89.2648 0.000000000) (list 83.3013 89.0662 0.000000000) (list 86.0000 89.0000 0.000000000))))
  (setq b (s16-extrude-y s16p 20 21 -381 171))
  (s16-sub a b)
  (s16-layer "$PART_S16_T-DOOR-L\U+02D90\U+02D90\U+00A8VVVV\U+02D90\U+00A8#0\U+00A816084" 34)
  (setq s16p nil)
  (setq s16p (append s16p (list (list 326.0000 83.0000 0.000000000) (list 328.9931 83.0735 0.000000000) (list 331.9790 83.2937 0.000000000) (list 334.9506 83.6602 0.000000000) (list 337.9005 84.1721 0.000000000) (list 340.8218 84.8281 0.000000000) (list 343.7074 85.6266 0.000000000) (list 346.5503 86.5658 0.000000000) (list 349.3437 87.6433 0.000000000) (list 352.0809 88.8567 0.000000000) (list 354.7552 90.2028 0.000000000) (list 357.3603 91.6786 0.000000000) (list 359.8898 93.2804 0.000000000) (list 362.3377 95.0043 0.000000000) (list 364.6980 96.8464 0.000000000) (list 366.9651 98.8020 0.000000000) (list 369.1335 100.8665 0.000000000) (list 371.1980 103.0349 0.000000000) (list 373.1536 105.3020 0.000000000) (list 374.9957 107.6623 0.000000000) (list 376.7196 110.1102 0.000000000) (list 378.3214 112.6397 0.000000000) (list 379.7972 115.2448 0.000000000) (list 381.1433 117.9191 0.000000000) (list 382.3567 120.6563 0.000000000) (list 383.4342 123.4497 0.000000000) (list 384.3734 126.2926 0.000000000) (list 385.1719 129.1782 0.000000000) (list 385.8279 132.0995 0.000000000) (list 386.3398 135.0494 0.000000000) (list 386.7063 138.0210 0.000000000) (list 386.9265 141.0069 0.000000000) (list 387.0000 144.0000 0.000000000) (list 387.0000 2539.0000 0.000000000) (list 386.9265 2541.9931 0.000000000) (list 386.7063 2544.9790 0.000000000) (list 386.3398 2547.9506 0.000000000) (list 385.8279 2550.9005 0.000000000) (list 385.1719 2553.8218 0.000000000) (list 384.3734 2556.7074 0.000000000))))
  (setq s16p (append s16p (list (list 383.4342 2559.5503 0.000000000) (list 382.3567 2562.3437 0.000000000) (list 381.1433 2565.0809 0.000000000) (list 379.7972 2567.7552 0.000000000) (list 378.3214 2570.3603 0.000000000) (list 376.7196 2572.8898 0.000000000) (list 374.9957 2575.3377 0.000000000) (list 373.1536 2577.6980 0.000000000) (list 371.1980 2579.9651 0.000000000) (list 369.1335 2582.1335 0.000000000) (list 366.9651 2584.1980 0.000000000) (list 364.6980 2586.1536 0.000000000) (list 362.3377 2587.9957 0.000000000) (list 359.8898 2589.7196 0.000000000) (list 357.3603 2591.3214 0.000000000) (list 354.7552 2592.7972 0.000000000) (list 352.0809 2594.1433 0.000000000) (list 349.3437 2595.3567 0.000000000) (list 346.5503 2596.4342 0.000000000) (list 343.7074 2597.3734 0.000000000) (list 340.8218 2598.1719 0.000000000) (list 337.9005 2598.8279 0.000000000) (list 334.9506 2599.3398 0.000000000) (list 331.9790 2599.7063 0.000000000) (list 328.9931 2599.9265 0.000000000) (list 326.0000 2600.0000 0.000000000) (list 86.0000 2600.0000 0.000000000) (list 83.0069 2599.9265 0.000000000) (list 80.0210 2599.7063 0.000000000) (list 77.0494 2599.3398 0.000000000) (list 74.0995 2598.8279 0.000000000) (list 71.1782 2598.1719 0.000000000) (list 68.2926 2597.3734 0.000000000) (list 65.4497 2596.4342 0.000000000) (list 62.6563 2595.3567 0.000000000) (list 59.9191 2594.1433 0.000000000) (list 57.2448 2592.7972 0.000000000) (list 54.6397 2591.3214 0.000000000) (list 52.1102 2589.7196 0.000000000) (list 49.6623 2587.9957 0.000000000))))
  (setq s16p (append s16p (list (list 47.3020 2586.1536 0.000000000) (list 45.0349 2584.1980 0.000000000) (list 42.8665 2582.1335 0.000000000) (list 40.8020 2579.9651 0.000000000) (list 38.8464 2577.6980 0.000000000) (list 37.0043 2575.3377 0.000000000) (list 35.2804 2572.8898 0.000000000) (list 33.6786 2570.3603 0.000000000) (list 32.2028 2567.7552 0.000000000) (list 30.8567 2565.0809 0.000000000) (list 29.6433 2562.3437 0.000000000) (list 28.5658 2559.5503 0.000000000) (list 27.6266 2556.7074 0.000000000) (list 26.8281 2553.8218 0.000000000) (list 26.1721 2550.9005 0.000000000) (list 25.6602 2547.9506 0.000000000) (list 25.2937 2544.9790 0.000000000) (list 25.0735 2541.9931 0.000000000) (list 25.0000 2539.0000 0.000000000) (list 25.0000 144.0000 0.000000000) (list 25.0735 141.0069 0.000000000) (list 25.2937 138.0210 0.000000000) (list 25.6602 135.0494 0.000000000) (list 26.1721 132.0995 0.000000000) (list 26.8281 129.1782 0.000000000) (list 27.6266 126.2926 0.000000000) (list 28.5658 123.4497 0.000000000) (list 29.6433 120.6563 0.000000000) (list 30.8567 117.9191 0.000000000) (list 32.2028 115.2448 0.000000000) (list 33.6786 112.6397 0.000000000) (list 35.2804 110.1102 0.000000000) (list 37.0043 107.6623 0.000000000) (list 38.8464 105.3020 0.000000000) (list 40.8020 103.0349 0.000000000) (list 42.8665 100.8665 0.000000000) (list 45.0349 98.8020 0.000000000) (list 47.3020 96.8464 0.000000000) (list 49.6623 95.0043 0.000000000) (list 52.1102 93.2804 0.000000000))))
  (setq s16p (append s16p (list (list 54.6397 91.6786 0.000000000) (list 57.2448 90.2028 0.000000000) (list 59.9191 88.8567 0.000000000) (list 62.6563 87.6433 0.000000000) (list 65.4497 86.5658 0.000000000) (list 68.2926 85.6266 0.000000000) (list 71.1782 84.8281 0.000000000) (list 74.0995 84.1721 0.000000000) (list 77.0494 83.6602 0.000000000) (list 80.0210 83.2937 0.000000000) (list 83.0069 83.0735 0.000000000) (list 86.0000 83.0000 0.000000000))))
  (setq b (s16-extrude-y s16p 11 21 -381 171))
  (s16-sub a b)
  ;; T-DOOR-R
  (s16-layer "$PART_S16_T-DOOR-R\U+02D90\U+02D90\U+00A8VVVV\U+02D90\U+00A8#0\U+00A816085" 34)
  (setq s16p nil)
  (setq s16p (append s16p (list (list 0.0000 0.0000 0.000000000) (list 412.5000 0.0000 0.000000000) (list 412.5000 2202.0000 0.414213562) (list 333.5000 2281.0000 0.000000000) (list 0.0000 2281.0000 0.000000000))))
  (setq a (s16-extrude-y s16p 18 436.5 -382 573))
  ;; TEXTILE
  (s16-layer "$PART_S16_TEXTILE\U+02D90\U+02D90\U+00A8KKKK\U+02D90\U+00A8#0\U+00A816086" 51)
  (setq s16p nil)
  (setq s16p (append s16p (list (list 300.0000 0.0000 0.414213562) (list 360.0000 60.0000 0.000000000) (list 360.0000 2455.0000 0.414213562) (list 300.0000 2515.0000 0.000000000) (list 60.0000 2515.0000 0.414213562) (list 0.0000 2455.0000 0.000000000) (list 0.0000 60.0000 0.414213562) (list 60.0000 0.0000 0.000000000))))
  (setq a (s16-extrude-y s16p 8 47 -366 255))
  ;; BG-1
  (s16-layer "$PART_S16_BG-1\U+02D90\U+02D90\U+00A80000\U+02D90\U+00A8#0\U+00A816087" 41)
  (setq a (s16-box 740 -25 470 811.0 17 2405))
  ;; BG-2
  (s16-layer "$PART_S16_BG-2\U+02D90\U+02D90\U+00A80000\U+02D90\U+00A8#0\U+00A816088" 41)
  (setq a (s16-box 1554.0 -25 470 679.5 17 2405))
  ;; BG-3
  (s16-layer "$PART_S16_BG-3\U+02D90\U+02D90\U+00A80000\U+02D90\U+00A8#0\U+00A816089" 41)
  (setq a (s16-box 2236.5 -25 470 679.5 17 2405))
  ;; BG-4
  (s16-layer "$PART_S16_BG-4\U+02D90\U+02D90\U+00A80000\U+02D90\U+00A8#0\U+00A816090" 41)
  (setq a (s16-box 2919 -25 470 678.0 17 2405))
  ;; BATTEN-1
  (s16-layer "$PART_S16_BATTEN-1\U+02D90\U+02D90\U+00A80000\U+02D90\U+00A8#0\U+00A816091" 254)
  (setq a (s16-box 910 -8 590 40 8 2235))
  ;; BATTEN-2
  (s16-layer "$PART_S16_BATTEN-2\U+02D90\U+02D90\U+00A80000\U+02D90\U+00A8#0\U+00A816092" 254)
  (setq a (s16-box 1540 -8 590 40 8 2235))
  ;; BATTEN-3
  (s16-layer "$PART_S16_BATTEN-3\U+02D90\U+02D90\U+00A80000\U+02D90\U+00A8#0\U+00A816093" 254)
  (setq a (s16-box 2220 -8 590 40 8 2235))
  ;; BATTEN-4
  (s16-layer "$PART_S16_BATTEN-4\U+02D90\U+02D90\U+00A80000\U+02D90\U+00A8#0\U+00A816094" 254)
  (setq a (s16-box 2900 -8 590 40 8 2235))
  ;; BATTEN-5
  (s16-layer "$PART_S16_BATTEN-5\U+02D90\U+02D90\U+00A80000\U+02D90\U+00A8#0\U+00A816095" 254)
  (setq a (s16-box 3530 -8 590 40 8 2235))
  ;; CURVE-T-TOP
  (s16-layer "$PART_S16_CURVE-T-TOP\U+02D90\U+02D90\U+00A8FFFF\U+02D90\U+00A8#0\U+00A816096" 250)
  (setq s16p nil)
  (setq s16p (append s16p (list (list 0.0000 0.0000 -0.414213562) (list 100.0000 100.0000 0.000000000) (list 770.0000 100.0000 -0.414213562) (list 870.0000 0.0000 0.000000000) (list 852.0000 0.0000 0.414213562) (list 770.0000 82.0000 0.000000000) (list 100.0000 82.0000 0.414213562) (list 18.0000 0.0000 0.000000000))))
  (setq a (s16-extrude-y s16p 337 0 -40 2775))
  ;; FRAME-T-TOP
  (s16-layer "$PART_S16_FRAME-T-TOP\U+02D90\U+02D90\U+00A8FFFF\U+02D90\U+00A8#0\U+00A816097" 250)
  (setq s16p nil)
  (setq s16p (append s16p (list (list 0.0000 0.0000 -0.414213562) (list 100.0000 100.0000 0.000000000) (list 770.0000 100.0000 -0.414213562) (list 870.0000 0.0000 0.000000000) (list 852.0000 0.0000 0.414213562) (list 770.0000 82.0000 0.000000000) (list 100.0000 82.0000 0.414213562) (list 18.0000 0.0000 0.000000000))))
  (setq a (s16-extrude-y s16p 18 0 -382 2775))
  ;; CURVE-T-BOT
  (s16-layer "$PART_S16_CURVE-T-BOT\U+02D90\U+02D90\U+00A8F0FF\U+02D90\U+00A8#0\U+00A816098" 250)
  (setq s16p nil)
  (setq s16p (append s16p (list (list 0.0000 100.0000 0.414213562) (list 100.0000 0.0000 0.000000000) (list 870.0000 0.0000 0.000000000) (list 870.0000 18.0000 0.000000000) (list 100.0000 18.0000 -0.414213562) (list 18.0000 100.0000 0.000000000))))
  (setq a (s16-extrude-y s16p 337 0 -40 150))
  ;; FRAME-T-BOT
  (s16-layer "$PART_S16_FRAME-T-BOT\U+02D90\U+02D90\U+00A8FFFF\U+02D90\U+00A8#0\U+00A816099" 250)
  (setq s16p nil)
  (setq s16p (append s16p (list (list 0.0000 100.0000 0.414213562) (list 100.0000 0.0000 0.000000000) (list 870.0000 0.0000 0.000000000) (list 870.0000 18.0000 0.000000000) (list 100.0000 18.0000 -0.414213562) (list 18.0000 100.0000 0.000000000))))
  (setq a (s16-extrude-y s16p 18 0 -382 150))
  ;; FRAME-T-L
  (s16-layer "$PART_S16_FRAME-T-L\U+02D90\U+02D90\U+00A80F0F\U+02D90\U+00A8#0\U+00A816100" 250)
  (setq a (s16-box 0 -400 250 18 18 2525))
  ;; FRAME-T-R
  (s16-layer "$PART_S16_FRAME-T-R\U+02D90\U+02D90\U+00A80F0F\U+02D90\U+00A8#0\U+00A816101" 250)
  (setq a (s16-box 852 -400 570 18 18 2205))
  ;; FRAME-T-MID
  (s16-layer "$PART_S16_FRAME-T-MID\U+02D90\U+02D90\U+00A8F0FF\U+02D90\U+00A8#0\U+00A816102" 250)
  (setq a (s16-box 436.5 -400 552 433.5 18 18))
  ;; FRAME-B-LOW-1
  (s16-layer "$PART_S16_FRAME-B-LOW-1\U+02D90\U+02D90\U+00A8F0F0\U+02D90\U+00A8#0\U+00A816103" 250)
  (setq a (s16-box 870 -400 150 850 18 18))
  ;; FRAME-B-LOW-2
  (s16-layer "$PART_S16_FRAME-B-LOW-2\U+02D90\U+02D90\U+00A8F0F0\U+02D90\U+00A8#0\U+00A816104" 250)
  (setq a (s16-box 1720 -400 150 1030 18 18))
  ;; FRAME-B-LOW-3
  (s16-layer "$PART_S16_FRAME-B-LOW-3\U+02D90\U+02D90\U+00A8F0F0\U+02D90\U+00A8#0\U+00A816105" 250)
  (setq a (s16-box 2750 -400 150 770 18 18))
  ;; FRAME-B-HIGH-1
  (s16-layer "$PART_S16_FRAME-B-HIGH-1\U+02D90\U+02D90\U+00A8F0F0\U+02D90\U+00A8#0\U+00A816106" 250)
  (setq a (s16-box 870 -400 552 850 18 18))
  ;; FRAME-B-HIGH-2
  (s16-layer "$PART_S16_FRAME-B-HIGH-2\U+02D90\U+02D90\U+00A8F0F0\U+02D90\U+00A8#0\U+00A816107" 250)
  (setq a (s16-box 1720 -400 552 1030 18 18))
  ;; FRAME-B-HIGH-3
  (s16-layer "$PART_S16_FRAME-B-HIGH-3\U+02D90\U+02D90\U+00A8F0F0\U+02D90\U+00A8#0\U+00A816108" 250)
  (setq a (s16-box 2750 -400 552 770 18 18))
  ;; FRAME-B-TOP
  (s16-layer "$PART_S16_FRAME-B-TOP\U+02D90\U+02D90\U+00A8FFFF\U+02D90\U+00A8#0\U+00A816109" 250)
  (setq s16p nil)
  (setq s16p (append s16p (list (list 0.0000 80.0000 -0.414213562) (list 80.0000 0.0000 0.000000000) (list 62.0000 0.0000 0.414213562) (list 0.0000 62.0000 0.000000000))))
  (setq a (s16-extrude-y s16p 18 3520 -382 490))
  ;; CURVE-B-TOP
  (s16-layer "$PART_S16_CURVE-B-TOP\U+02D90\U+02D90\U+00A8FFFF\U+02D90\U+00A8#0\U+00A816110" 250)
  (setq s16p nil)
  (setq s16p (append s16p (list (list 0.0000 80.0000 -0.414213562) (list 80.0000 0.0000 0.000000000) (list 62.0000 0.0000 0.414213562) (list 0.0000 62.0000 0.000000000))))
  (setq a (s16-extrude-y s16p 337 3520 -40 490))
  ;; FRAME-B-BOT
  (s16-layer "$PART_S16_FRAME-B-BOT\U+02D90\U+02D90\U+00A8FFFF\U+02D90\U+00A8#0\U+00A816111" 250)
  (setq s16p nil)
  (setq s16p (append s16p (list (list 0.0000 18.0000 0.414213562) (list 62.0000 80.0000 0.000000000) (list 80.0000 80.0000 -0.414213562) (list 0.0000 0.0000 0.000000000))))
  (setq a (s16-extrude-y s16p 18 3520 -382 150))
  ;; CURVE-B-BOT
  (s16-layer "$PART_S16_CURVE-B-BOT\U+02D90\U+02D90\U+00A8FFFF\U+02D90\U+00A8#0\U+00A816112" 250)
  (setq s16p nil)
  (setq s16p (append s16p (list (list 0.0000 18.0000 0.414213562) (list 62.0000 80.0000 0.000000000) (list 80.0000 80.0000 -0.414213562) (list 0.0000 0.0000 0.000000000))))
  (setq a (s16-extrude-y s16p 337 3520 -40 150))
  ;; FRAME-B-R
  (s16-layer "$PART_S16_FRAME-B-R\U+02D90\U+02D90\U+00A80F0F\U+02D90\U+00A8#0\U+00A816113" 250)
  (setq a (s16-box 3582 -400 230 18 18 260))
  ;; TV-SPACER-1
  (s16-layer "$PART_S16_TV-SPACER-1\U+02D90\U+02D90\U+00A8FFFF\U+02D90\U+00A8#0\U+00A816114" 250)
  (setq a (s16-box 910 -95 605 2530 69 30))
  ;; TV-SPACER-2
  (s16-layer "$PART_S16_TV-SPACER-2\U+02D90\U+02D90\U+00A8FFFF\U+02D90\U+00A8#0\U+00A816115" 250)
  (setq a (s16-box 1340 -95 2050 2020 69 30))
  ;; T-LOW-DIV
  (s16-layer "$PART_S16_T-LOW-DIV\U+02D90\U+02D90\U+00A80V00\U+02D90\U+00A8#0\U+00A816116" 8)
  (setq a (s16-box 417 -377 168 18 337 402))
  ;; T-LOW-BACK
  (s16-layer "$PART_S16_T-LOW-BACK\U+02D90\U+02D90\U+00A80000\U+02D90\U+00A8#0\U+00A816117" 9)
  (setq s16p nil)
  (setq s16p (append s16p (list (list 0.0000 402.0000 0.000000000) (list 399.0000 402.0000 0.000000000) (list 399.0000 0.0000 0.000000000) (list 82.0000 0.0000 -0.414213562) (list 0.0000 82.0000 0.000000000))))
  (setq a (s16-extrude-y s16p 8 18 -40 168))
  ;; T-DOOR-L-BACK
  (s16-layer "$PART_S16_T-DOOR-L-BACK\U+02D90\U+02D90\U+00A8FFFF\U+02D90\U+00A8#0\U+00A816118" 250)
  (setq s16p nil)
  (setq s16p (append s16p (list (list 305.0000 0.0000 0.000000000) (list 308.1894 0.0783 0.000000000) (list 311.3711 0.3130 0.000000000) (list 314.5375 0.7035 0.000000000) (list 317.6809 1.2490 0.000000000) (list 320.7937 1.9480 0.000000000) (list 323.8685 2.7989 0.000000000) (list 326.8978 3.7996 0.000000000) (list 329.8744 4.9478 0.000000000) (list 332.7911 6.2407 0.000000000) (list 335.6408 7.6751 0.000000000) (list 338.4167 9.2476 0.000000000) (list 341.1121 10.9545 0.000000000) (list 343.7205 12.7915 0.000000000) (list 346.2356 14.7543 0.000000000) (list 348.6513 16.8382 0.000000000) (list 350.9619 19.0381 0.000000000) (list 353.1618 21.3487 0.000000000) (list 355.2457 23.7644 0.000000000) (list 357.2085 26.2795 0.000000000) (list 359.0455 28.8879 0.000000000) (list 360.7524 31.5833 0.000000000) (list 362.3249 34.3592 0.000000000) (list 363.7593 37.2089 0.000000000) (list 365.0522 40.1256 0.000000000) (list 366.2004 43.1022 0.000000000) (list 367.2011 46.1315 0.000000000) (list 368.0520 49.2063 0.000000000) (list 368.7510 52.3191 0.000000000) (list 369.2965 55.4625 0.000000000) (list 369.6870 58.6289 0.000000000) (list 369.9217 61.8106 0.000000000) (list 370.0000 65.0000 0.000000000) (list 370.0000 2460.0000 0.000000000) (list 369.9217 2463.1894 0.000000000) (list 369.6870 2466.3711 0.000000000) (list 369.2965 2469.5375 0.000000000) (list 368.7510 2472.6809 0.000000000) (list 368.0520 2475.7937 0.000000000) (list 367.2011 2478.8685 0.000000000))))
  (setq s16p (append s16p (list (list 366.2004 2481.8978 0.000000000) (list 365.0522 2484.8744 0.000000000) (list 363.7593 2487.7911 0.000000000) (list 362.3249 2490.6408 0.000000000) (list 360.7524 2493.4167 0.000000000) (list 359.0455 2496.1121 0.000000000) (list 357.2085 2498.7205 0.000000000) (list 355.2457 2501.2356 0.000000000) (list 353.1618 2503.6513 0.000000000) (list 350.9619 2505.9619 0.000000000) (list 348.6513 2508.1618 0.000000000) (list 346.2356 2510.2457 0.000000000) (list 343.7205 2512.2085 0.000000000) (list 341.1121 2514.0455 0.000000000) (list 338.4167 2515.7524 0.000000000) (list 335.6408 2517.3249 0.000000000) (list 332.7911 2518.7593 0.000000000) (list 329.8744 2520.0522 0.000000000) (list 326.8978 2521.2004 0.000000000) (list 323.8685 2522.2011 0.000000000) (list 320.7937 2523.0520 0.000000000) (list 317.6809 2523.7510 0.000000000) (list 314.5375 2524.2965 0.000000000) (list 311.3711 2524.6870 0.000000000) (list 308.1894 2524.9217 0.000000000) (list 305.0000 2525.0000 0.000000000) (list 65.0000 2525.0000 0.000000000) (list 61.8106 2524.9217 0.000000000) (list 58.6289 2524.6870 0.000000000) (list 55.4625 2524.2965 0.000000000) (list 52.3191 2523.7510 0.000000000) (list 49.2063 2523.0520 0.000000000) (list 46.1315 2522.2011 0.000000000) (list 43.1022 2521.2004 0.000000000) (list 40.1256 2520.0522 0.000000000) (list 37.2089 2518.7593 0.000000000) (list 34.3592 2517.3249 0.000000000) (list 31.5833 2515.7524 0.000000000) (list 28.8879 2514.0455 0.000000000) (list 26.2795 2512.2085 0.000000000))))
  (setq s16p (append s16p (list (list 23.7644 2510.2457 0.000000000) (list 21.3487 2508.1618 0.000000000) (list 19.0381 2505.9619 0.000000000) (list 16.8382 2503.6513 0.000000000) (list 14.7543 2501.2356 0.000000000) (list 12.7915 2498.7205 0.000000000) (list 10.9545 2496.1121 0.000000000) (list 9.2476 2493.4167 0.000000000) (list 7.6751 2490.6408 0.000000000) (list 6.2407 2487.7911 0.000000000) (list 4.9478 2484.8744 0.000000000) (list 3.7996 2481.8978 0.000000000) (list 2.7989 2478.8685 0.000000000) (list 1.9480 2475.7937 0.000000000) (list 1.2490 2472.6809 0.000000000) (list 0.7035 2469.5375 0.000000000) (list 0.3130 2466.3711 0.000000000) (list 0.0783 2463.1894 0.000000000) (list 0.0000 2460.0000 0.000000000) (list 0.0000 65.0000 0.000000000) (list 0.0783 61.8106 0.000000000) (list 0.3130 58.6289 0.000000000) (list 0.7035 55.4625 0.000000000) (list 1.2490 52.3191 0.000000000) (list 1.9480 49.2063 0.000000000) (list 2.7989 46.1315 0.000000000) (list 3.7996 43.1022 0.000000000) (list 4.9478 40.1256 0.000000000) (list 6.2407 37.2089 0.000000000) (list 7.6751 34.3592 0.000000000) (list 9.2476 31.5833 0.000000000) (list 10.9545 28.8879 0.000000000) (list 12.7915 26.2795 0.000000000) (list 14.7543 23.7644 0.000000000) (list 16.8382 21.3487 0.000000000) (list 19.0381 19.0381 0.000000000) (list 21.3487 16.8382 0.000000000) (list 23.7644 14.7543 0.000000000) (list 26.2795 12.7915 0.000000000) (list 28.8879 10.9545 0.000000000))))
  (setq s16p (append s16p (list (list 31.5833 9.2476 0.000000000) (list 34.3592 7.6751 0.000000000) (list 37.2089 6.2407 0.000000000) (list 40.1256 4.9478 0.000000000) (list 43.1022 3.7996 0.000000000) (list 46.1315 2.7989 0.000000000) (list 49.2063 1.9480 0.000000000) (list 52.3191 1.2490 0.000000000) (list 55.4625 0.7035 0.000000000) (list 58.6289 0.3130 0.000000000) (list 61.8106 0.0783 0.000000000) (list 65.0000 0.0000 0.000000000))))
  (setq a (s16-extrude-y s16p 12 42 -354 250))
  ;; TV-FIELD
  (s16-layer "TECH_FENYCSATORNA_FALC_S16_TV-FIELD" 1)
  (setq b (s16-box 869 -114 569 2629 13 27))
  (s16-layer "$PART_S16_TV-FIELD\U+02D90\U+02D90\U+00A8VVVV\U+02D90\U+00A8#0\U+00A816119" 34)
  (setq s16p nil)
  (setq s16p (append s16p (list (list 0.0000 0.0000 0.000000000) (list 2630.0000 0.0000 0.000000000) (list 2630.0000 100.0000 0.000000000) (list 2630.0000 1480.0000 0.000000000) (list 2629.8795 1484.9068 0.000000000) (list 2629.5185 1489.8017 0.000000000) (list 2628.9177 1494.6730 0.000000000) (list 2628.0785 1499.5090 0.000000000) (list 2627.0031 1504.2980 0.000000000) (list 2625.6940 1509.0285 0.000000000) (list 2624.1544 1513.6890 0.000000000) (list 2622.3880 1518.2683 0.000000000) (list 2620.3989 1522.7555 0.000000000) (list 2618.1921 1527.1397 0.000000000) (list 2615.7729 1531.4103 0.000000000) (list 2613.1470 1535.5570 0.000000000) (list 2610.3208 1539.5699 0.000000000) (list 2607.3010 1543.4393 0.000000000) (list 2604.0951 1547.1559 0.000000000) (list 2600.7107 1550.7107 0.000000000) (list 2597.1559 1554.0951 0.000000000) (list 2593.4393 1557.3010 0.000000000) (list 2589.5699 1560.3208 0.000000000) (list 2585.5570 1563.1470 0.000000000) (list 2581.4103 1565.7729 0.000000000) (list 2577.1397 1568.1921 0.000000000) (list 2572.7555 1570.3989 0.000000000) (list 2568.2683 1572.3880 0.000000000) (list 2563.6890 1574.1544 0.000000000) (list 2559.0285 1575.6940 0.000000000) (list 2554.2980 1577.0031 0.000000000) (list 2549.5090 1578.0785 0.000000000) (list 2544.6730 1578.9177 0.000000000) (list 2539.8017 1579.5185 0.000000000) (list 2534.9068 1579.8795 0.000000000) (list 2530.0000 1580.0000 0.000000000) (list 450.0000 1580.0000 0.000000000) (list 443.1305 1579.8314 0.000000000) (list 436.2776 1579.3259 0.000000000) (list 429.4577 1578.4847 0.000000000))))
  (setq s16p (append s16p (list (list 422.6874 1577.3099 0.000000000) (list 415.9828 1575.8044 0.000000000) (list 409.3601 1573.9716 0.000000000) (list 402.8354 1571.8162 0.000000000) (list 396.4243 1569.3431 0.000000000) (list 390.1423 1566.5585 0.000000000) (list 384.0045 1563.4690 0.000000000) (list 378.0256 1560.0820 0.000000000) (list 372.2202 1556.4057 0.000000000) (list 366.6021 1552.4491 0.000000000) (list 361.1849 1548.2215 0.000000000) (list 355.9817 1543.7332 0.000000000) (list 351.0051 1538.9949 0.000000000) (list 346.2668 1534.0183 0.000000000) (list 341.7785 1528.8151 0.000000000) (list 337.5509 1523.3979 0.000000000) (list 333.5943 1517.7798 0.000000000) (list 329.9180 1511.9744 0.000000000) (list 326.5310 1505.9955 0.000000000) (list 323.4415 1499.8577 0.000000000) (list 320.6569 1493.5757 0.000000000) (list 318.1838 1487.1646 0.000000000) (list 316.0284 1480.6399 0.000000000) (list 314.1956 1474.0172 0.000000000) (list 312.6901 1467.3126 0.000000000) (list 311.5153 1460.5423 0.000000000) (list 310.6741 1453.7224 0.000000000) (list 310.1686 1446.8695 0.000000000) (list 310.0000 1440.0000 0.000000000) (list 310.0000 540.0000 0.000000000) (list 309.8073 532.1492 0.000000000) (list 309.2296 524.3173 0.000000000) (list 308.2682 516.5231 0.000000000) (list 306.9256 508.7855 0.000000000) (list 305.2050 501.1232 0.000000000) (list 303.1105 493.5545 0.000000000) (list 300.6471 486.0976 0.000000000) (list 297.8207 478.7707 0.000000000) (list 294.6383 471.5912 0.000000000) (list 291.1074 464.5765 0.000000000))))
  (setq s16p (append s16p (list (list 287.2366 457.7436 0.000000000) (list 283.0351 451.1088 0.000000000) (list 278.5132 444.6881 0.000000000) (list 273.6817 438.4971 0.000000000) (list 268.5522 432.5506 0.000000000) (list 263.1371 426.8629 0.000000000) (list 257.4494 421.4478 0.000000000) (list 251.5029 416.3183 0.000000000) (list 245.3119 411.4868 0.000000000) (list 238.8912 406.9649 0.000000000) (list 232.2564 402.7634 0.000000000) (list 225.4235 398.8926 0.000000000) (list 218.4088 395.3617 0.000000000) (list 211.2293 392.1793 0.000000000) (list 203.9024 389.3529 0.000000000) (list 196.4455 386.8895 0.000000000) (list 188.8768 384.7950 0.000000000) (list 181.2145 383.0744 0.000000000) (list 173.4769 381.7318 0.000000000) (list 165.6827 380.7704 0.000000000) (list 157.8508 380.1927 0.000000000) (list 150.0000 380.0000 0.000000000) (list 0.0000 380.0000 0.000000000))))
  (setq a (s16-extrude-y s16p 18 870 -95 570))
  (s16-layer "$PART_S16_TV-FIELD\U+02D90\U+02D90\U+00A8VVVV\U+02D90\U+00A8#0\U+00A816119" 34)
  (setq b (s16-box 869 -114 569 2629 13 27))
  (s16-sub a b)
  ;; BG-FINISH
  (s16-layer "$PART_S16_BG-FINISH\U+02D90\U+02D90\U+00A80000\U+02D90\U+00A8#0\U+00A816120" 41)
  (setq a (s16-box 740 -26 470 2857 1 2405))
  ;; TOP-WASH-COVER
  (s16-layer "$PART_S16_TOP-WASH-COVER\U+02D90\U+02D90\U+00A80000\U+02D90\U+00A8#0\U+00A816121" 1)
  (setq a (s16-box 740.0 -34.0 2872.0 2857.0 8.0 3.0))
  ;; TOP-WASH-BAFFLE
  (s16-layer "$PART_S16_TOP-WASH-BAFFLE\U+02D90\U+02D90\U+00A80000\U+02D90\U+00A8#0\U+00A816122" 1)
  (setq a (s16-box 740.0 -38.0 2857.0 2857.0 4.0 18.0))
  ;; TOP-WASH-HIDDEN-END
  (s16-layer "$PART_S16_TOP-WASH-HIDDEN-END\U+02D90\U+02D90\U+00A80000\U+02D90\U+00A8#0\U+00A816123" 1)
  (setq a (s16-box 3595.0 -34.0 2857.0 2.0 8.0 15.0))
  ;; UPLIGHT-TRAY
  (s16-layer "$PART_S16_UPLIGHT-TRAY\U+02D90\U+02D90\U+00A80000\U+02D90\U+00A8#0\U+00A816124" 1)
  (setq a (s16-box 740.0 -29.0 2875.0 2845.0 24.0 1.0))
  ;; UPLIGHT-FRONT-VISOR
  (s16-layer "$PART_S16_UPLIGHT-FRONT-VISOR\U+02D90\U+02D90\U+00A80000\U+02D90\U+00A8#0\U+00A816125" 1)
  (setq a (s16-box 740.0 -29.0 2876.0 2845.0 4.0 3.0))
  ;; UPLIGHT-REAR-VISOR
  (s16-layer "$PART_S16_UPLIGHT-REAR-VISOR\U+02D90\U+02D90\U+00A80000\U+02D90\U+00A8#0\U+00A816126" 1)
  (setq a (s16-box 740.0 -8.0 2876.0 2845.0 3.0 3.0))
  ;; DECK-CONTINUOUS-COVER
  (s16-layer "$PART_S16_DECK-CONTINUOUS-COVER\U+02D90\U+02D90\U+00A80000\U+02D90\U+00A8#0\U+00A816127" 1)
  (setq a (s16-box 870.0 -109.0 592.0 2628.0 8.0 4.0))
  ;; DECK-CONTINUOUS-BAFFLE
  (s16-layer "$PART_S16_DECK-CONTINUOUS-BAFFLE\U+02D90\U+02D90\U+00A80000\U+02D90\U+00A8#0\U+00A816128" 1)
  (setq a (s16-box 870.0 -113.0 579.0 2628.0 4.0 17.0))
  ;; LOW-INTERNAL-LIGHT-VISOR
  (s16-layer "$PART_S16_LOW-INTERNAL-LIGHT-VISOR\U+02D90\U+02D90\U+00A80000\U+02D90\U+00A8#0\U+00A816129" 1)
  (setq a (s16-box 57.0 -348.0 554.0 306.0 5.0 16.0))
  (command "_.ZOOM" "_E")
  (princ "\nS16 R15: 129 alkatrész felépítve.")
  (princ))
(princ "\nS16 betöltve: (s16-build) majd (s16-readback \"/Users/<te>/CAD/s16_readback\")")
(princ)
